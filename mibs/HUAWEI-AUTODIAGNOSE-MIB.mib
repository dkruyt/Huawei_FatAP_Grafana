-- ============================================================================
-- Copyright (C) 2014 by  HUAWEI TECHNOLOGIES. All rights reserved.
-- Description: This mib is used for autodiagnose
-- Reference: None
-- Version:   V1.00
-- ============================================================================
--
-- HUAWEI-AUTODIAGNOSE-MIB.my
-- MIB generated by MG-SOFT Visual MIB Builder Version 4.0 Build 341
-- Thursday, December 04, 2014 at 19:32:03
--

	HUAWEI-AUTODIAGNOSE-MIB DEFINITIONS ::= BEGIN
		IMPORTS   
			hwWlan			
				FROM HUAWEI-WLAN-MIB
			Integer32			
				FROM SNMPv2-SMI
			MacAddress, DateAndTime, RowStatus		
				FROM SNMPv2-TC 
			MODULE-COMPLIANCE, OBJECT-GROUP
                                                                                     FROM SNMPv2-CONF
			IpAddress,MODULE-IDENTITY, OBJECT-TYPE
			                     FROM SNMPv2-SMI;    
			    
		-- 1.3.6.1.4.1.2011.6.139.10	    
		hwAutodiag MODULE-IDENTITY	  
 
			LAST-UPDATED "201405041600Z"		-- May 4, 2014 at 16:00 GMT
			ORGANIZATION 
				"Huawei Technologies Co.,Ltd."
			CONTACT-INFO 
                                                                                       "Huawei Industrial Base
				   Bantian, Longgang
				   Shenzhen 518129
				   People's Republic of China
				   Website: http://www.huawei.com
				   Email: support@huawei.com
				  "
			DESCRIPTION 
				"The MIB module include wids informations."
			REVISION "201405041600Z"		-- May 08, 2012 at 00:00 GMT
			DESCRIPTION 
				"
				V1.00, Inital version.
				"
			::= { hwWlan 10}			    
--       
-- Node definitions
--
	
		-- 1.3.6.1.4.1.2011.6.139.10.1          
		hwAutoDiagnoseTable OBJECT-TYPE
			SYNTAX SEQUENCE OF HwAutoDiagnoseEntry
			MAX-ACCESS not-accessible
			STATUS current
			DESCRIPTION
			"Diagnostic task information table."
			::= { hwAutodiag 1 }

		
		-- 1.3.6.1.4.1.2011.6.139.10.1.1
		hwAutoDiagnoseEntry OBJECT-TYPE
			SYNTAX HwAutoDiagnoseEntry    
			MAX-ACCESS not-accessible
			STATUS current
			DESCRIPTION
			"Diagnostic task information table entry."
			INDEX { hwAutoDiagnoseTaskID }
			::= { hwAutoDiagnoseTable 1 }

		
		HwAutoDiagnoseEntry ::=
			SEQUENCE { 
				hwAutoDiagnoseIssueType
					Integer32,
				hwAutoDiagnoseIssueID
					Integer32,
				hwAutoDiagnoseObjetcMac
					MacAddress,
				hwAutoDiagnoseObjetcIP
					IpAddress,
				hwAutoDiagnoseObjetcIPv6
					OCTET STRING,
				hwAutoDiagnoseObjectName
					OCTET STRING,
				hwAutoDiagnoseObjetcGatewayIP
					IpAddress,
				hwAutoDiagnoseObjetcGatewayIPv6
					OCTET STRING,
				hwAutoDiagnoseStartTime
					DateAndTime,
				hwAutoDiagnoseTaskTimerangeStartTime
					DateAndTime,      				
				hwAutoDiagnoseTaskTimerangeEndTime
					DateAndTime,
				hwAutoDiagnoseTaskStatus
					Integer32,
				hwAutoDiagnoseTaskType
					Integer32,
				hwAutoDiagnoseTaskID
					Integer32,  
				hwAutoDiagnoseRowStatus
					RowStatus
			 }

		-- 1.3.6.1.4.1.2011.6.139.10.1.1.1
		hwAutoDiagnoseIssueType OBJECT-TYPE
			SYNTAX Integer32
			MAX-ACCESS read-write
			STATUS current
			DESCRIPTION
			"autodiagnose issue type,
       AC(1)
       AP(2)
       WIRELESS-STA(3)
       WIRED-STA(4) "
			::= { hwAutoDiagnoseEntry 1 }

		
		-- 1.3.6.1.4.1.2011.6.139.10.1.1.2
		hwAutoDiagnoseIssueID OBJECT-TYPE
			SYNTAX Integer32
			MAX-ACCESS read-write
			STATUS current
			DESCRIPTION
			"autodiagnose issue id,
			 sta online fail (1)  
			 sta offline (2) 
			 wiredless-sta usage abnormal(3) 
			 ap offline or online fail(4) 
			 ap device exception(5)  
			 ac device exception(6) 
			 upgrade fail(7)  
			 wired-sta usage abnormal(8) "
			::= { hwAutoDiagnoseEntry 2 }

		
		-- 1.3.6.1.4.1.2011.6.139.10.1.1.3
		hwAutoDiagnoseObjetcMac OBJECT-TYPE
			SYNTAX MacAddress
			MAX-ACCESS read-write
			STATUS current              
			DESCRIPTION
			"appoint autodiagnose-object mac-address."
			::= { hwAutoDiagnoseEntry 3 }

		
		-- 1.3.6.1.4.1.2011.6.139.10.1.1.4
		hwAutoDiagnoseObjetcIP OBJECT-TYPE
			SYNTAX IpAddress
			MAX-ACCESS read-write
			STATUS current
			DESCRIPTION
			"appoint autodiagnose-object ip-address."
			::= { hwAutoDiagnoseEntry 4 }

		
		-- 1.3.6.1.4.1.2011.6.139.10.1.1.5
		hwAutoDiagnoseObjetcIPv6 OBJECT-TYPE
			SYNTAX OCTET STRING
			MAX-ACCESS read-write
			STATUS current
			DESCRIPTION
			"appoint autodiagnose-object ipv6-address."
			::= { hwAutoDiagnoseEntry 5 }

		
		-- 1.3.6.1.4.1.2011.6.139.10.1.1.6
		hwAutoDiagnoseObjectName OBJECT-TYPE
			SYNTAX OCTET STRING
			MAX-ACCESS read-write
			STATUS current
			DESCRIPTION
			"appoint autodiagnose-object name."
			::= { hwAutoDiagnoseEntry 6 }

		
		-- 1.3.6.1.4.1.2011.6.139.10.1.1.7
		hwAutoDiagnoseObjetcGatewayIP OBJECT-TYPE
			SYNTAX IpAddress
			MAX-ACCESS read-write
			STATUS current
			DESCRIPTION
			"appoint autodiagnose-object gateway-ipaddress."
			::= { hwAutoDiagnoseEntry 7 }

		
		-- 1.3.6.1.4.1.2011.6.139.10.1.1.8
		hwAutoDiagnoseObjetcGatewayIPv6 OBJECT-TYPE
			SYNTAX OCTET STRING
			MAX-ACCESS read-write
			STATUS current
			DESCRIPTION
			"appoint autodiagnose-object gateway-ipv6-address."
			::= { hwAutoDiagnoseEntry 8 }

		
		-- 1.3.6.1.4.1.2011.6.139.10.1.1.9
		hwAutoDiagnoseStartTime OBJECT-TYPE
			SYNTAX DateAndTime
			MAX-ACCESS read-write
			STATUS current
			DESCRIPTION
			"appoint autodiagnose-task start time."
			::= { hwAutoDiagnoseEntry 9 }

			
		-- 1.3.6.1.4.1.2011.6.139.10.1.1.10
		hwAutoDiagnoseTaskTimerangeStartTime OBJECT-TYPE
			SYNTAX DateAndTime
			MAX-ACCESS read-write
			STATUS current
			DESCRIPTION
			"appoint autodiagnose-task time-range start time.the end time is later than start time"
			::= { hwAutoDiagnoseEntry 10 }
			
		-- 1.3.6.1.4.1.2011.6.139.10.1.1.11
		hwAutoDiagnoseTaskTimerangeEndTime OBJECT-TYPE
			SYNTAX DateAndTime
			MAX-ACCESS read-write
			STATUS current
			DESCRIPTION
			"appoint task time-range end time.the end time is later than start time"
			::= { hwAutoDiagnoseEntry 11 }
		
		-- 1.3.6.1.4.1.2011.6.139.10.1.1.12
		hwAutoDiagnoseTaskStatus OBJECT-TYPE
			SYNTAX Integer32
			MAX-ACCESS read-only
			STATUS current
			DESCRIPTION
			"appoint task status. 
			 IDLE(1) 
			 WAITTING(2) 
			 READY(3)
			 RUNNING(4) 
			 DONE(5) 
			 DEAD(6)"
			::= { hwAutoDiagnoseEntry 12 }

		
		-- 1.3.6.1.4.1.2011.6.139.10.1.1.13
		hwAutoDiagnoseTaskType OBJECT-TYPE
			SYNTAX Integer32
			MAX-ACCESS read-only
			STATUS current
			DESCRIPTION
			"appoint task type. 
			 Timer task(1) 
			 Real time task(2)"
			::= { hwAutoDiagnoseEntry 13 }

		
		-- 1.3.6.1.4.1.2011.6.139.10.1.1.14
		hwAutoDiagnoseTaskID OBJECT-TYPE
			SYNTAX Integer32
			MAX-ACCESS read-write
			STATUS current
			DESCRIPTION
			"appoint task id.id 0 is real time task id-region <1-5> is timer task"
			::= { hwAutoDiagnoseEntry 14 }

					      
		-- 1.3.6.1.4.1.2011.6.139.10.1.1.15
		hwAutoDiagnoseRowStatus OBJECT-TYPE
			SYNTAX RowStatus
			MAX-ACCESS read-create
			STATUS current
			DESCRIPTION
			"appoint create or delete task."
			::= { hwAutoDiagnoseEntry 15 }


		-- 1.3.6.1.4.1.2011.6.139.10.2
		hwAutoDiagnoseIssueResultTable OBJECT-TYPE
			SYNTAX SEQUENCE OF HwAutoDiagnoseIssueResultEntry
			MAX-ACCESS not-accessible
			STATUS current
			DESCRIPTION
			"appoint task issue result table."
			::= { hwAutodiag 2 }

		
		-- 1.3.6.1.4.1.2011.6.139.10.2.1    
		hwAutoDiagnoseIssueResultEntry OBJECT-TYPE
			SYNTAX HwAutoDiagnoseIssueResultEntry
			MAX-ACCESS not-accessible
			STATUS current
			DESCRIPTION
			"appoint task issue result table entry."
			INDEX { hwAutoDiagnoseTaskID,hwAutoDiagnoseIssueIndex }
			::= { hwAutoDiagnoseIssueResultTable 1 }

		
		HwAutoDiagnoseIssueResultEntry ::=
			SEQUENCE { 
				hwAutoDiagnoseIssueIndex
					Integer32,     
				hwAutoDiagnoseIssueIdNum
				  Integer32,
				hwAutoDiagnoseIssueResult
					Integer32,
				hwAutoDiagnoseIssueStatus
					Integer32,
				hwAutoDiagnoseIssueSuggestion
					OCTET STRING
					 }
		
		-- 1.3.6.1.4.1.2011.6.139.10.2.1.1
		hwAutoDiagnoseIssueIndex OBJECT-TYPE
			SYNTAX Integer32
			MAX-ACCESS read-write
			STATUS current
			DESCRIPTION
			"appoint task issue index."
			::= { hwAutoDiagnoseIssueResultEntry 1 }     
			
		-- 1.3.6.1.4.1.2011.6.139.10.2.1.2
		hwAutoDiagnoseIssueIdNum OBJECT-TYPE
			SYNTAX Integer32
			MAX-ACCESS read-only
			STATUS current
			DESCRIPTION
			"appoint task issue id,
			 sta online fail (1)  
			 sta offline (2) 
			 wireless-sta usage abnormal(3) 
			 ap offline or online fail(4) 
			 ap device exception(5)  
			 ac device exception(6) 
			 upgrade fail(7)  
			 wired-sta usage abnormal(8)"
			::= { hwAutoDiagnoseIssueResultEntry 2 }


		                                                          
		-- 1.3.6.1.4.1.2011.6.139.10.2.1.3
		hwAutoDiagnoseIssueResult OBJECT-TYPE
			SYNTAX Integer32
			MAX-ACCESS read-only
			STATUS current
			DESCRIPTION
			"appoint task issue result. 
			no problem(1) 
			exist problem(2) 
			potential problem(3) 
			exec fail(4)"
			::= { hwAutoDiagnoseIssueResultEntry 3 }

		
		-- 1.3.6.1.4.1.2011.6.139.10.2.1.4
		hwAutoDiagnoseIssueStatus OBJECT-TYPE
			SYNTAX Integer32
			MAX-ACCESS read-only
			STATUS current
			DESCRIPTION
			"appoint autodiagnose-task issue execute status.waitting(1) running(2) done(3)"
			::= { hwAutoDiagnoseIssueResultEntry 4 }

		
		-- 1.3.6.1.4.1.2011.6.139.10.2.1.5
		hwAutoDiagnoseIssueSuggestion OBJECT-TYPE
			SYNTAX OCTET STRING
			MAX-ACCESS read-only
			STATUS current
			DESCRIPTION
			"appoint autodiagnose-task issue execute suggestion."
			::= { hwAutoDiagnoseIssueResultEntry 5 }
			
		-- 1.3.6.1.4.1.2011.6.139.10.3
		hwAutoDiagnoseSubIssueResultTable OBJECT-TYPE
			SYNTAX SEQUENCE OF HwAutoDiagnoseSubIssueResultEntry
			MAX-ACCESS not-accessible
			STATUS current
			DESCRIPTION
			"appoint autodiagnose-task sub-issue execute result.  
			 no problem(1) 
			 exist problem(2) 
			 potential problem(3) 
			 execute fail(4)"
			::= { hwAutodiag 3 }

		
		-- 1.3.6.1.4.1.2011.6.139.10.3.1
		hwAutoDiagnoseSubIssueResultEntry OBJECT-TYPE
			SYNTAX HwAutoDiagnoseSubIssueResultEntry
			MAX-ACCESS not-accessible
			STATUS current
			DESCRIPTION
			"appoint autodiagnose-task sub-issue execute result table."
			INDEX { hwAutoDiagnoseTaskID, hwAutoDiagnoseIssueIndex, hwAutoDiagnoseSubIssueIndex }
			::= { hwAutoDiagnoseSubIssueResultTable 1 }

		
		HwAutoDiagnoseSubIssueResultEntry ::=
			SEQUENCE { 
				hwAutoDiagnoseSubIssueIndex
					Integer32,
				hwAutoDiagnoseSubIssueId
					Integer32,
				hwAutoDiagnoseSubIssueStatus
					Integer32,
				hwAutoDiagnoseSubIssueResult
					Integer32,
				hwAutoDiagnoseSubIssueFaultReason
			    OCTET STRING,
			  hwAutoDiagnoseSubIssueFaultDealSuggestion
			    OCTET STRING
					 }     
					 
		-- 1.3.6.1.4.1.2011.6.139.10.3.1.1
		hwAutoDiagnoseSubIssueIndex OBJECT-TYPE
			SYNTAX Integer32
			MAX-ACCESS read-write
			STATUS current
			DESCRIPTION
			"appoint autodiagnose-task sub-issue execute result table index."
			::= { hwAutoDiagnoseSubIssueResultEntry 1 }
			
		-- 1.3.6.1.4.1.2011.6.139.10.3.1.2 
		hwAutoDiagnoseSubIssueId OBJECT-TYPE
			SYNTAX Integer32
			MAX-ACCESS read-only
			STATUS current
			DESCRIPTION
			"appoint task sub-issue id.
      STA association authentication(1),
      STA association authentication and key negotiation(2) ,                     
      STA IP address obtaining(3),                                      
      Wireless packet receiving and forwarding parameters(4),              
      STA indicators(5),              
      Environment interference indicators(6),                            
      Multi-STA environment indicators(7),                          
      Service configuration(8),                
      AC's CPU usage(9),                                       
      CPU usage of the AP with which the STA associates(10),                                                         
      AC's memory usage(11),                     
      Memory usage of the AP with which the STA associates(12),                     
      Service test over the wireless bridge link(13),           
      Wireless bridge configuration(14), 
      Wireless bridge link(15),          
      Packet receiving and forwarding parameters of an abnormal node(16),            
      Abnormal node indicators(17),           
      Environment interference indicators of an abnormal node(18),      
      Multi-STA environment indicators of an abnormal node(19),      
      STA offline record(20),                         
      STA service simulation test(21),                   
      Packet forwarding inside a device(22),                    
      AP online failure record(23),                       
      AP offline record(24),                      
      AP IP address obtaining(25),                             
      Test of the network between the AC and AP(26),                  
      Link establishment failure record of wireless bridge nodes(27),         
      Link disconnection record of wireless bridge nodes(28),        
      Diagnosis(29),                  
      AP upgrade process diagnosis(30),                    
      Service test over the upgrade channel(31),               
      Diagnosis(32),                                                                              
      ftp server test(33)"
			::= { hwAutoDiagnoseSubIssueResultEntry 2 }     
			
		-- 1.3.6.1.4.1.2011.6.139.10.3.1.3
		hwAutoDiagnoseSubIssueStatus OBJECT-TYPE
			SYNTAX Integer32
			MAX-ACCESS read-only
			STATUS current
			DESCRIPTION
			"describe sub-issue execute status,
			 waitting(1) 
			 running(2) 
			 done(3)."
			::= { hwAutoDiagnoseSubIssueResultEntry 3 }

		-- 1.3.6.1.4.1.2011.6.139.10.3.1.4
		hwAutoDiagnoseSubIssueResult OBJECT-TYPE
			SYNTAX Integer32
			MAX-ACCESS read-only
			STATUS current
			DESCRIPTION
			"describe sub-issue execute result
			no problem(1) 
			exist problem(2) 
			potential problem(3) 
			exec fail(4)."
			::= { hwAutoDiagnoseSubIssueResultEntry 4 }

		-- 1.3.6.1.4.1.2011.6.139.10.3.1.5
		hwAutoDiagnoseSubIssueFaultReason OBJECT-TYPE
			SYNTAX OCTET STRING
			MAX-ACCESS read-only
			STATUS current
			DESCRIPTION
			"describe the subissue fault reason."
			::= { hwAutoDiagnoseSubIssueResultEntry 5 }

		-- 1.3.6.1.4.1.2011.6.139.10.3.1.6
		hwAutoDiagnoseSubIssueFaultDealSuggestion OBJECT-TYPE
			SYNTAX OCTET STRING
			MAX-ACCESS read-only
			STATUS current
			DESCRIPTION
			"describe the subissue suggestion."
			::= { hwAutoDiagnoseSubIssueResultEntry 6 }

		-- 1.3.6.1.4.1.2011.6.139.10.4
		hwAutoDiagnoseSubIssueDetailResultTable OBJECT-TYPE
			SYNTAX SEQUENCE OF HwAutoDiagnoseSubIssueDetailResultEntry
			MAX-ACCESS not-accessible
			STATUS current
			DESCRIPTION
			"describe subissue-detail result table."
			::= { hwAutodiag 4 }

		
		-- 1.3.6.1.4.1.2011.6.139.10.4.1
		hwAutoDiagnoseSubIssueDetailResultEntry OBJECT-TYPE
			SYNTAX HwAutoDiagnoseSubIssueDetailResultEntry
			MAX-ACCESS not-accessible
			STATUS current
			DESCRIPTION
			"describe subissue-detail result table-entry."
			INDEX { hwAutoDiagnoseTaskID,hwAutoDiagnoseIssueIndex, hwAutoDiagnoseSubIssueIndex, hwAutoDiagnoseSubIssueDetailIndex }
			::= { hwAutoDiagnoseSubIssueDetailResultTable 1 }

		HwAutoDiagnoseSubIssueDetailResultEntry ::=
			SEQUENCE { 
				hwAutoDiagnoseSubIssueDetailIndex
					Integer32,      
			    hwAutoDiagnoseSubIssueDetailResult
					Integer32,
				hwAutoDiagnoseSubIssueDetailFaultReason
					OCTET STRING,
				hwAutoDiagnoseSubIssueDetailFaultDealSuggestion
					OCTET STRING
					 }
					  
		-- 1.3.6.1.4.1.2011.6.139.10.4.1.1
		hwAutoDiagnoseSubIssueDetailIndex OBJECT-TYPE
			SYNTAX Integer32
			MAX-ACCESS read-write
			STATUS current
			DESCRIPTION
			"subissue-detail result table index."
			::= { hwAutoDiagnoseSubIssueDetailResultEntry 1 }  
			
		-- 1.3.6.1.4.1.2011.6.139.10.4.1.2
		hwAutoDiagnoseSubIssueDetailResult OBJECT-TYPE
			SYNTAX Integer32
			MAX-ACCESS read-only
			STATUS current
			DESCRIPTION
			"subissue-detail result 
			 no problem(1) 
			 exist problem(2) 
			 potential problem(3) 
			 exec fail(4)."
			::= { hwAutoDiagnoseSubIssueDetailResultEntry 2 }    
						      
		-- 1.3.6.1.4.1.2011.6.139.10.4.1.3
		hwAutoDiagnoseSubIssueDetailFaultReason OBJECT-TYPE
			SYNTAX OCTET STRING
			MAX-ACCESS read-only
			STATUS current
			DESCRIPTION
			"subissue-detail result reason."
			::= { hwAutoDiagnoseSubIssueDetailResultEntry 3 }    

		-- 1.3.6.1.4.1.2011.6.139.10.4.1.4
		hwAutoDiagnoseSubIssueDetailFaultDealSuggestion OBJECT-TYPE
			SYNTAX OCTET STRING
			MAX-ACCESS read-only
			STATUS current
			DESCRIPTION
			"subissue-detail result suggestion."
			::= { hwAutoDiagnoseSubIssueDetailResultEntry 4 }
			

		-- 1.3.6.1.4.1.2011.6.139.10.5
		hwAutoDiagnoseConformance OBJECT IDENTIFIER ::= { hwAutodiag 5 }

		
		-- 1.3.6.1.4.1.2011.6.139.10.5.1
		hwAutoDiagnoseCompliances OBJECT IDENTIFIER ::= { hwAutoDiagnoseConformance 1 }

		
		-- 1.3.6.1.4.1.2011.6.139.10.5.1.1
		hwAutoDiagnoseCompliance MODULE-COMPLIANCE
			STATUS current
			DESCRIPTION 
			"Description."
      MODULE 
			::= { hwAutoDiagnoseCompliances 1 }

		
		-- 1.3.6.1.4.1.2011.6.139.10.5.2
		hwAutoDiagnoseObjectGroups OBJECT IDENTIFIER ::= { hwAutoDiagnoseConformance 2 }				
		
		-- 1.3.6.1.4.1.2011.6.139.10.5.2.1
		hwAutoDiagnosetGroups OBJECT-GROUP
			OBJECTS { hwAutoDiagnoseIssueType, hwAutoDiagnoseIssueID,hwAutoDiagnoseObjetcMac,hwAutoDiagnoseObjetcIP,
                      hwAutoDiagnoseObjetcIPv6, hwAutoDiagnoseObjectName, hwAutoDiagnoseObjetcGatewayIP,hwAutoDiagnoseObjetcGatewayIPv6,
                      hwAutoDiagnoseStartTime, hwAutoDiagnoseTaskTimerangeStartTime, hwAutoDiagnoseTaskTimerangeEndTime,
                      hwAutoDiagnoseTaskStatus, hwAutoDiagnoseTaskType, hwAutoDiagnoseTaskID, hwAutoDiagnoseRowStatus
                     }
			STATUS current
			DESCRIPTION 
				"Description."
			::= { hwAutoDiagnoseObjectGroups 1 }

		-- 1.3.6.1.4.1.2011.6.139.10.5.2.2
		hwAutoDiagnosetIssueResultGroups OBJECT-GROUP
			OBJECTS { hwAutoDiagnoseIssueIndex, hwAutoDiagnoseIssueIdNum, hwAutoDiagnoseIssueResult, hwAutoDiagnoseIssueStatus,hwAutoDiagnoseIssueSuggestion }
			STATUS current
			DESCRIPTION 
				"Description."
			::= { hwAutoDiagnoseObjectGroups 2 }    
			 
		-- 1.3.6.1.4.1.2011.6.139.10.5.2.3
		hwAutoDiagnosetSubIssueResultGroups OBJECT-GROUP
			OBJECTS { hwAutoDiagnoseSubIssueIndex, hwAutoDiagnoseSubIssueId, hwAutoDiagnoseSubIssueStatus,
				      hwAutoDiagnoseSubIssueResult, hwAutoDiagnoseSubIssueFaultReason, hwAutoDiagnoseSubIssueFaultDealSuggestion
				    }
			STATUS current
			DESCRIPTION 
				"Description."
			::= { hwAutoDiagnoseObjectGroups 3 }         

		-- 1.3.6.1.4.1.2011.6.139.10.5.2.4
		hwAutoDiagnosetSubIssueDetailResultGroups OBJECT-GROUP
			OBJECTS { hwAutoDiagnoseSubIssueDetailIndex,hwAutoDiagnoseSubIssueDetailResult, hwAutoDiagnoseSubIssueDetailFaultReason,
				      hwAutoDiagnoseSubIssueDetailFaultDealSuggestion
				    }
			STATUS current
			DESCRIPTION 
				"Description."
			::= { hwAutoDiagnoseObjectGroups 4 }					
	
	END
         
--
-- HUAWEI-AUTODIAGNOSE-MIB.my
--
