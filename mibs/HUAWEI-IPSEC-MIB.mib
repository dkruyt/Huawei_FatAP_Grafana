-- Copyright (C) 2015 by HUAWEI TECHNOLOGIES. All rights reserved.
--
-- HUAWEI-IPSEC-MIB_0316.mib
-- MIB generated by Visual MIB Builder Version 3.0 Build 253
-- Friday, March 16, 2012 at 11:04:12
--

--  HUAWEI-IPSEC-MIB.mib
-- MIB generated by Visual MIB Builder Version 3.0 Build 253
-- Monday, May 09, 2011 at 11:49:33
-- 
--  HUAWEI-IPSEC-MIB001.mib
-- MIB generated by Visual MIB Builder Version 3.0 Build 253
-- Friday, April 01, 2011 at 11:15:25
-- Version:V2.16

	HUAWEI-IPSEC-MIB DEFINITIONS ::= BEGIN
 
		IMPORTS
			hwDatacomm			
				FROM HUAWEI-MIB			
			EnabledStatus			
				FROM P-BRIDGE-MIB			
			OBJECT-GROUP, MODULE-COMPLIANCE, NOTIFICATION-GROUP			
				FROM SNMPv2-CONF			
			TimeTicks, IpAddress, Integer32, Gauge32, Counter64, OBJECT-TYPE, 
			MODULE-IDENTITY, NOTIFICATION-TYPE			
				FROM SNMPv2-SMI			
			RowStatus			
				FROM SNMPv2-TC;
	
	
--  Jan 14, 2014 at 18:55 GMT
		hwIPSecMIB MODULE-IDENTITY 
                                                       LAST-UPDATED "201511241018Z"		-- Sept 22, 2015 at 11:35 GMT
			ORGANIZATION 
				 "Huawei Technologies Co.,Ltd."
			CONTACT-INFO 
				"Huawei Industrial Base
				  Bantian, Longgang
				   Shenzhen 518129
				   People's Republic of China
				   Website: http://www.huawei.com
				   Email: support@huawei.com
				 "
                                                         DESCRIPTION 
				"Description."
                                             
                                                   REVISION "201511241018Z"
                                                   DESCRIPTION
                                                         "modify table of ipsec mutiboard performance monitor ."

                                                   REVISION "201509221135Z"
                                                   DESCRIPTION
                                                         "add a new table for ipsec mutiboard performance monitor ."

                                                   REVISION "201401141855Z"
                                                   DESCRIPTION
                                                        "add a new table for ipsec performance monitor ."

                                                  REVISION "201309181636Z"
	                               DESCRIPTION
				"add two new trap nodes and change the order of the VB value of some nodes ."

                                                  REVISION "201308281856Z"
			DESCRIPTION
				"change the order of the VB value of some nodes ."
                                                     REVISION "201307071535Z"
			DESCRIPTION
				"add three new nodes ."
                                                           			::= { hwDatacomm 224 }
	
	
--
-- Node definitions
--
	
--  Node definitions
-- 
-- Node definitions
-- 
-- 1.3.6.1.4.1.2011.5.25.224.1
-- 1.3.6.1.4.1.2011.5.25.224.1
		-- 1.3.6.1.4.1.2011.5.25.224.1
		hwIPSecObjects OBJECT IDENTIFIER ::= { hwIPSecMIB 1 }
		
--   1.3.6.1.4.1.2011.5.25.224.1.1
-- 1.3.6.1.4.1.2011.5.25.224.1.1
		-- 1.3.6.1.4.1.2011.5.25.224.1.1
		hwIPSecScalar OBJECT IDENTIFIER ::= { hwIPSecObjects 1 }
		
--   1.3.6.1.4.1.2011.5.25.224.1.1.1
-- 1.3.6.1.4.1.2011.5.25.224.1.1.1
		-- 1.3.6.1.4.1.2011.5.25.224.1.1.1
		hwIPSecIkeSaTimeout OBJECT-TYPE
			SYNTAX Integer32 (0 | 30..3600)
			UNITS "s"
			MAX-ACCESS read-write
			STATUS current
			DESCRIPTION
				"Description."
			DEFVAL { '0'b }
			::= { hwIPSecScalar 1 }
		
--   1.3.6.1.4.1.2011.5.25.224.1.1.2
-- 1.3.6.1.4.1.2011.5.25.224.1.1.2
		-- 1.3.6.1.4.1.2011.5.25.224.1.1.2
		hwIPSecIkeSaInterval OBJECT-TYPE
			SYNTAX Integer32 (0 | 30..3600)
			UNITS "s"
			MAX-ACCESS read-write
			STATUS current
			DESCRIPTION
				"Description."
			DEFVAL { '0'b }
			::= { hwIPSecScalar 2 }
		
--   1.3.6.1.4.1.2011.5.25.224.1.1.3
-- 1.3.6.1.4.1.2011.5.25.224.1.1.3
		-- 1.3.6.1.4.1.2011.5.25.224.1.1.3
		hwIPSecIkeUndoLocalname OBJECT-TYPE
			SYNTAX EnabledStatus
			MAX-ACCESS read-write
			STATUS current
			DESCRIPTION
				"Description."
			DEFVAL { disabled }
			::= { hwIPSecScalar 3 }
		
--   1.3.6.1.4.1.2011.5.25.224.1.1.4
-- 1.3.6.1.4.1.2011.5.25.224.1.1.4
		-- 1.3.6.1.4.1.2011.5.25.224.1.1.4
		hwIPSecIkeLocalname OBJECT-TYPE
			SYNTAX OCTET STRING (SIZE (0..15))
			MAX-ACCESS read-write
			STATUS current
			DESCRIPTION
				"Description."
			::= { hwIPSecScalar 4 }
		
--   1.3.6.1.4.1.2011.5.25.224.1.1.5
-- 1.3.6.1.4.1.2011.5.25.224.1.1.5
		-- 1.3.6.1.4.1.2011.5.25.224.1.1.5
		hwIPSecIkeSaNatInterval OBJECT-TYPE
			SYNTAX Integer32 (5..300)
			UNITS "s"
			MAX-ACCESS read-write
			STATUS current
			DESCRIPTION
				"Description."
			DEFVAL { 20 }
			::= { hwIPSecScalar 5 }
		
--   1.3.6.1.4.1.2011.5.25.224.1.1.6
-- 1.3.6.1.4.1.2011.5.25.224.1.1.6
		-- 1.3.6.1.4.1.2011.5.25.224.1.1.6
		hwIPSecSecSaGlobalDurationTraffic OBJECT-TYPE
			SYNTAX Integer32 (8000..200000000)
			UNITS "KB"
			MAX-ACCESS read-write
			STATUS current
			DESCRIPTION
				"Description."
			DEFVAL { 1843200 }
			::= { hwIPSecScalar 6 }
		
--   1.3.6.1.4.1.2011.5.25.224.1.1.7
-- 1.3.6.1.4.1.2011.5.25.224.1.1.7
		-- 1.3.6.1.4.1.2011.5.25.224.1.1.7
		hwIPSecSecSaGlobalDurationTimebased OBJECT-TYPE
			SYNTAX Integer32 (480..604800)
			MAX-ACCESS read-write
			STATUS current
			DESCRIPTION
				"Description."
			DEFVAL { 3600 }
			::= { hwIPSecScalar 7 }
		
--   1.3.6.1.4.1.2011.5.25.224.1.1.8
-- 1.3.6.1.4.1.2011.5.25.224.1.1.8
		-- 1.3.6.1.4.1.2011.5.25.224.1.1.8
		hwIPSecSecPreCheck OBJECT-TYPE
			SYNTAX EnabledStatus
			MAX-ACCESS read-write
			STATUS current
			DESCRIPTION
				"Description."
			DEFVAL { disabled }
			::= { hwIPSecScalar 8 }
		
--   1.3.6.1.4.1.2011.5.25.224.1.1.9
-- 1.3.6.1.4.1.2011.5.25.224.1.1.9
		-- 1.3.6.1.4.1.2011.5.25.224.1.1.9
		hwIPSecSecSucceedCheck OBJECT-TYPE
			SYNTAX EnabledStatus
			MAX-ACCESS read-write
			STATUS current
			DESCRIPTION
				"Description."
			DEFVAL { disabled }
			::= { hwIPSecScalar 9 }
		
--   1.3.6.1.4.1.2011.5.25.224.1.1.10
-- 1.3.6.1.4.1.2011.5.25.224.1.1.10
		-- 1.3.6.1.4.1.2011.5.25.224.1.1.10
		hwIPSecSecGlobalFragmentation OBJECT-TYPE
			SYNTAX EnabledStatus
			MAX-ACCESS read-write
			STATUS current
			DESCRIPTION
				"Description."
			DEFVAL { disabled }
			::= { hwIPSecScalar 10 }
		
--   1.3.6.1.4.1.2011.5.25.224.1.1.11
-- 1.3.6.1.4.1.2011.5.25.224.1.1.11
		-- 1.3.6.1.4.1.2011.5.25.224.1.1.11
		hwIPSecSecGlobalDfBitClear OBJECT-TYPE
			SYNTAX EnabledStatus
			MAX-ACCESS read-write
			STATUS current
			DESCRIPTION
				"Description."
			DEFVAL { disabled }
			::= { hwIPSecScalar 11 }
		
--   1.3.6.1.4.1.2011.5.25.224.1.1.12
-- 1.3.6.1.4.1.2011.5.25.224.1.1.12
		-- 1.3.6.1.4.1.2011.5.25.224.1.1.12
		hwIPSecSecGlobalFilterPolicyImportAcl OBJECT-TYPE
			SYNTAX Integer32 (0 | 3000..3999)
			MAX-ACCESS read-write
			STATUS current
			DESCRIPTION
				"Description."
			DEFVAL { ''b }
			::= { hwIPSecScalar 12 }
		
--   1.3.6.1.4.1.2011.5.25.224.1.1.13
-- 1.3.6.1.4.1.2011.5.25.224.1.1.13
		-- 1.3.6.1.4.1.2011.5.25.224.1.1.13
		hwIPSecSecGlobalFilterPolicyExportAcl OBJECT-TYPE
			SYNTAX Integer32 (0 | 3000..3999)
			MAX-ACCESS read-write
			STATUS current
			DESCRIPTION
				"Description."
			DEFVAL { ''b }
			::= { hwIPSecScalar 13 }
		
--  1.3.6.1.4.1.2011.5.25.224.1.1.14
		-- 1.3.6.1.4.1.2011.5.25.224.1.1.14
		hwIPSecPkiCrlChkEnable OBJECT-TYPE
			SYNTAX EnabledStatus
			MAX-ACCESS read-write
			STATUS current
			DESCRIPTION
				"Description."
			DEFVAL { disabled }
			::= { hwIPSecScalar 14 }
		
--  1.3.6.1.4.1.2011.5.25.224.1.1.15
		-- 1.3.6.1.4.1.2011.5.25.224.1.1.15
		hwIPSecPkiFileFmt OBJECT-TYPE
			SYNTAX INTEGER
				{
				der(0),
				pem(1)
				}
			MAX-ACCESS read-write
			STATUS current
			DESCRIPTION
				"Description."
			DEFVAL { pem }
			::= { hwIPSecScalar 15 }
		
--   1.3.6.1.4.1.2011.5.25.224.1.2
-- 1.3.6.1.4.1.2011.5.25.224.1.2
		-- 1.3.6.1.4.1.2011.5.25.224.1.2
		hwIPSecSlotBindTable OBJECT-TYPE
			SYNTAX SEQUENCE OF HwIPSecSlotBindEntry
			MAX-ACCESS not-accessible
			STATUS current
			DESCRIPTION
				"Description."
			::= { hwIPSecObjects 2 }
		
--   1.3.6.1.4.1.2011.5.25.224.1.2.1
-- 1.3.6.1.4.1.2011.5.25.224.1.2.1
		-- 1.3.6.1.4.1.2011.5.25.224.1.2.1
		hwIPSecSlotBindEntry OBJECT-TYPE
			SYNTAX HwIPSecSlotBindEntry
			MAX-ACCESS not-accessible
			STATUS current
			DESCRIPTION
				"Description."
			INDEX { hwIPSecSlotBindInstanceID, hwIPSecBackupID, hwIPSecBindSlotID }
			::= { hwIPSecSlotBindTable 1 }
		
		HwIPSecSlotBindEntry ::=
			SEQUENCE { 
				hwIPSecSlotBindInstanceID
					Integer32,
				hwIPSecBackupID
					Integer32,
				hwIPSecBindSlotID
					Integer32,
				hwIpsecInstanceStatus
					INTEGER,
				hwIpsecInstanceActiveSlotNum
					Integer32,
				hwIPSecBindSlotRowStatus
					RowStatus
			 }

--   1.3.6.1.4.1.2011.5.25.224.1.2.1.1
-- 1.3.6.1.4.1.2011.5.25.224.1.2.1.1
		-- 1.3.6.1.4.1.2011.5.25.224.1.2.1.1
		hwIPSecSlotBindInstanceID OBJECT-TYPE
			SYNTAX Integer32 (1..8)
			MAX-ACCESS read-only
			STATUS current
			DESCRIPTION
				"Description."
			::= { hwIPSecSlotBindEntry 1 }
		
--   1.3.6.1.4.1.2011.5.25.224.1.2.1.2
-- 1.3.6.1.4.1.2011.5.25.224.1.2.1.2
		-- 1.3.6.1.4.1.2011.5.25.224.1.2.1.2
		hwIPSecBackupID OBJECT-TYPE
			SYNTAX Integer32 (1..8)
			MAX-ACCESS read-only
			STATUS current
			DESCRIPTION
				"Description."
			::= { hwIPSecSlotBindEntry 2 }
		
--   1.3.6.1.4.1.2011.5.25.224.1.2.1.2
-- 1.3.6.1.4.1.2011.5.25.224.1.2.1.2
		-- 1.3.6.1.4.1.2011.5.25.224.1.2.1.3
		hwIPSecBindSlotID OBJECT-TYPE
			SYNTAX Integer32 (1..16)
			MAX-ACCESS read-only
			STATUS current
			DESCRIPTION
				"Description."
			::= { hwIPSecSlotBindEntry 3 }
		
		-- 1.3.6.1.4.1.2011.5.25.224.1.2.1.4
		hwIpsecInstanceStatus OBJECT-TYPE
			SYNTAX INTEGER
				{
				down(0),
				up(1)
				}
			MAX-ACCESS read-only
			STATUS current
			DESCRIPTION
				"Description."
			::= { hwIPSecSlotBindEntry 4 }
		
		-- 1.3.6.1.4.1.2011.5.25.224.1.2.1.5
		hwIpsecInstanceActiveSlotNum OBJECT-TYPE
			SYNTAX Integer32 (1..16)
			MAX-ACCESS read-only
			STATUS current
			DESCRIPTION
				"Description."
			::= { hwIPSecSlotBindEntry 5 }
		
--   1.3.6.1.4.1.2011.5.25.224.1.2.1.3
-- 1.3.6.1.4.1.2011.5.25.224.1.2.1.3
		-- 1.3.6.1.4.1.2011.5.25.224.1.2.1.6
		hwIPSecBindSlotRowStatus OBJECT-TYPE
			SYNTAX RowStatus
			MAX-ACCESS read-create
			STATUS current
			DESCRIPTION
				"Description."
			DEFVAL { active }
			::= { hwIPSecSlotBindEntry 6 }
		
--   1.3.6.1.4.1.2011.5.25.224.1.3
-- 1.3.6.1.4.1.2011.5.25.224.1.3
		-- 1.3.6.1.4.1.2011.5.25.224.1.3
		hwIPSecPeerTrackTable OBJECT-TYPE
			SYNTAX SEQUENCE OF HwIPSecPeerTrackEntry
			MAX-ACCESS not-accessible
			STATUS current
			DESCRIPTION
				"Description."
			::= { hwIPSecObjects 3 }
		
--   1.3.6.1.4.1.2011.5.25.224.1.3.1
-- 1.3.6.1.4.1.2011.5.25.224.1.3.1
		-- 1.3.6.1.4.1.2011.5.25.224.1.3.1
		hwIPSecPeerTrackEntry OBJECT-TYPE
			SYNTAX HwIPSecPeerTrackEntry
			MAX-ACCESS not-accessible
			STATUS current
			DESCRIPTION
				"Description."
			INDEX { hwIPSecPeerInstanceID }
			::= { hwIPSecPeerTrackTable 1 }
		
		HwIPSecPeerTrackEntry ::=
			SEQUENCE { 
				hwIPSecPeerInstanceID
					Integer32,
				hwIPSecPeerAddr
					IpAddress,
				hwIPSecSourceAddr
					IpAddress,
				hwIPSecStartPort
					Integer32,
				hwIPSecEndPort
					Integer32,
				hwIpsecTrackInterfaceName
					OCTET STRING,
				hwIPSecPeerRowStatus
					RowStatus
			 }

--   1.3.6.1.4.1.2011.5.25.224.1.2.1.1
-- 1.3.6.1.4.1.2011.5.25.224.1.2.1.1
		-- 1.3.6.1.4.1.2011.5.25.224.1.3.1.1
		hwIPSecPeerInstanceID OBJECT-TYPE
			SYNTAX Integer32 (1..8)
			MAX-ACCESS read-only
			STATUS current
			DESCRIPTION
				"Description."
			::= { hwIPSecPeerTrackEntry 1 }
		
--   1.3.6.1.4.1.2011.5.25.224.1.3.1.2
-- 1.3.6.1.4.1.2011.5.25.224.1.3.1.2
		-- 1.3.6.1.4.1.2011.5.25.224.1.3.1.2
		hwIPSecPeerAddr OBJECT-TYPE
			SYNTAX IpAddress
			MAX-ACCESS read-write
			STATUS current
			DESCRIPTION
				"Description."
			::= { hwIPSecPeerTrackEntry 2 }
		
--   1.3.6.1.4.1.2011.5.25.224.1.3.1.2
-- 1.3.6.1.4.1.2011.5.25.224.1.3.1.2
		-- 1.3.6.1.4.1.2011.5.25.224.1.3.1.3
		hwIPSecSourceAddr OBJECT-TYPE
			SYNTAX IpAddress
			MAX-ACCESS read-write
			STATUS current
			DESCRIPTION
				"Description."
			::= { hwIPSecPeerTrackEntry 3 }
		
--   1.3.6.1.4.1.2011.5.25.224.1.2.1.1
-- 1.3.6.1.4.1.2011.5.25.224.1.2.1.1
		-- 1.3.6.1.4.1.2011.5.25.224.1.3.1.4
		hwIPSecStartPort OBJECT-TYPE
			SYNTAX Integer32 (1025..65503)
			MAX-ACCESS read-write
			STATUS current
			DESCRIPTION
				"Description."
			DEFVAL { 18415 }
			::= { hwIPSecPeerTrackEntry 4 }
		
--   1.3.6.1.4.1.2011.5.25.224.1.3.1.1
-- 1.3.6.1.4.1.2011.5.25.224.1.3.1.1
		-- 1.3.6.1.4.1.2011.5.25.224.1.3.1.5
		hwIPSecEndPort OBJECT-TYPE
			SYNTAX Integer32 (1057..65535)
			MAX-ACCESS read-write
			STATUS current
			DESCRIPTION
				"Description."
			DEFVAL { 18447 }
			::= { hwIPSecPeerTrackEntry 5 }
		
--   1.3.6.1.4.1.2011.5.25.224.1.4.1.1
-- 1.3.6.1.4.1.2011.5.25.224.1.4.1.1
		-- 1.3.6.1.4.1.2011.5.25.224.1.3.1.6
		hwIpsecTrackInterfaceName OBJECT-TYPE
			SYNTAX OCTET STRING (SIZE (0..47))
			MAX-ACCESS read-write
			STATUS current
			DESCRIPTION
				"Description."
			::= { hwIPSecPeerTrackEntry 6 }
		
--   1.3.6.1.4.1.2011.5.25.224.1.3.1.3
-- 1.3.6.1.4.1.2011.5.25.224.1.3.1.3
		-- 1.3.6.1.4.1.2011.5.25.224.1.3.1.7
		hwIPSecPeerRowStatus OBJECT-TYPE
			SYNTAX RowStatus
			MAX-ACCESS read-create
			STATUS current
			DESCRIPTION
				"Description."
			DEFVAL { active }
			::= { hwIPSecPeerTrackEntry 7 }
		
--   1.3.6.1.4.1.2011.5.25.224.1.4
-- 1.3.6.1.4.1.2011.5.25.224.1.4
		-- 1.3.6.1.4.1.2011.5.25.224.1.4
		hwIPSecBindVrrpTable OBJECT-TYPE
			SYNTAX SEQUENCE OF HwIPSecBindVrrpEntry
			MAX-ACCESS not-accessible
			STATUS current
			DESCRIPTION
				"Description."
			::= { hwIPSecObjects 4 }
		
--   1.3.6.1.4.1.2011.5.25.224.1.4.1
-- 1.3.6.1.4.1.2011.5.25.224.1.4.1
		-- 1.3.6.1.4.1.2011.5.25.224.1.4.1
		hwIPSecBindVrrpEntry OBJECT-TYPE
			SYNTAX HwIPSecBindVrrpEntry
			MAX-ACCESS not-accessible
			STATUS current
			DESCRIPTION
				"Description."
			INDEX { hwIPSecVrrpInstanceID, hwIPSecVrrpInterfaceName, hwIPSecVrrpVrid }
			::= { hwIPSecBindVrrpTable 1 }
		
		HwIPSecBindVrrpEntry ::=
			SEQUENCE { 
				hwIPSecVrrpInstanceID
					Integer32,
				hwIPSecVrrpInterfaceName
					OCTET STRING,
				hwIPSecVrrpVrid
					Integer32,
				hwIPSecVrrpRowStatus
					RowStatus
			 }

--   1.3.6.1.4.1.2011.5.25.224.1.2.1.1
-- 1.3.6.1.4.1.2011.5.25.224.1.2.1.1
		-- 1.3.6.1.4.1.2011.5.25.224.1.4.1.1
		hwIPSecVrrpInstanceID OBJECT-TYPE
			SYNTAX Integer32 (1..8)
			MAX-ACCESS read-only
			STATUS current
			DESCRIPTION
				"Description."
			::= { hwIPSecBindVrrpEntry 1 }
		
--   1.3.6.1.4.1.2011.5.25.224.1.4.1.1
-- 1.3.6.1.4.1.2011.5.25.224.1.4.1.1
		-- 1.3.6.1.4.1.2011.5.25.224.1.4.1.2
		hwIPSecVrrpInterfaceName OBJECT-TYPE
			SYNTAX OCTET STRING (SIZE (0..47))
			MAX-ACCESS read-only
			STATUS current
			DESCRIPTION
				"Description."
			::= { hwIPSecBindVrrpEntry 2 }
		
--   1.3.6.1.4.1.2011.5.25.224.1.4.1.2
-- 1.3.6.1.4.1.2011.5.25.224.1.4.1.2
		-- 1.3.6.1.4.1.2011.5.25.224.1.4.1.3
		hwIPSecVrrpVrid OBJECT-TYPE
			SYNTAX Integer32 (1..255)
			MAX-ACCESS read-only
			STATUS current
			DESCRIPTION
				"Description."
			::= { hwIPSecBindVrrpEntry 3 }
		
--   1.3.6.1.4.1.2011.5.25.224.1.4.1.3
-- 1.3.6.1.4.1.2011.5.25.224.1.4.1.3
		-- 1.3.6.1.4.1.2011.5.25.224.1.4.1.4
		hwIPSecVrrpRowStatus OBJECT-TYPE
			SYNTAX RowStatus
			UNITS "active"
			MAX-ACCESS read-create
			STATUS current
			DESCRIPTION
				"Description."
			::= { hwIPSecBindVrrpEntry 4 }
		
--   1.3.6.1.4.1.2011.5.25.224.1.4
-- 1.3.6.1.4.1.2011.5.25.224.1.4
		-- 1.3.6.1.4.1.2011.5.25.224.1.5
		hwIPSecLeastActSlotTable OBJECT-TYPE
			SYNTAX SEQUENCE OF HwIPSecLeastActSlotEntry
			MAX-ACCESS not-accessible
			STATUS current
			DESCRIPTION
				"Description."
			::= { hwIPSecObjects 5 }
		
--   1.3.6.1.4.1.2011.5.25.224.1.4.1
-- 1.3.6.1.4.1.2011.5.25.224.1.4.1
		-- 1.3.6.1.4.1.2011.5.25.224.1.5.1
		hwIPSecLeastActSlotEntry OBJECT-TYPE
			SYNTAX HwIPSecLeastActSlotEntry
			MAX-ACCESS not-accessible
			STATUS current
			DESCRIPTION
				"Description."
			INDEX { hwIPSecLASInstanceID }
			::= { hwIPSecLeastActSlotTable 1 }
		
		HwIPSecLeastActSlotEntry ::=
			SEQUENCE { 
				hwIPSecLASInstanceID
					Integer32,
				hwIPSecLASlotNum
					Integer32,
				hwIPSecLASRowStatus
					RowStatus
			 }

--   1.3.6.1.4.1.2011.5.25.224.1.4.1.1
-- 1.3.6.1.4.1.2011.5.25.224.1.4.1.1
		-- 1.3.6.1.4.1.2011.5.25.224.1.5.1.1
		hwIPSecLASInstanceID OBJECT-TYPE
			SYNTAX Integer32 (1..8)
			MAX-ACCESS read-only
			STATUS current
			DESCRIPTION
				"Description."
			::= { hwIPSecLeastActSlotEntry 1 }
		
--   1.3.6.1.4.1.2011.5.25.224.1.4.1.2
-- 1.3.6.1.4.1.2011.5.25.224.1.4.1.2
		-- 1.3.6.1.4.1.2011.5.25.224.1.5.1.2
		hwIPSecLASlotNum OBJECT-TYPE
			SYNTAX Integer32 (0..8)
			MAX-ACCESS read-write
			STATUS current
			DESCRIPTION
				"Description."
			::= { hwIPSecLeastActSlotEntry 2 }
		
--   1.3.6.1.4.1.2011.5.25.224.1.4.1.3
-- 1.3.6.1.4.1.2011.5.25.224.1.4.1.3
		-- 1.3.6.1.4.1.2011.5.25.224.1.5.1.3
		hwIPSecLASRowStatus OBJECT-TYPE
			SYNTAX RowStatus
			MAX-ACCESS read-only
			STATUS current
			DESCRIPTION
				"Description."
			DEFVAL { active }
			::= { hwIPSecLeastActSlotEntry 3 }
		
--   1.3.6.1.4.1.2011.5.25.224.1.5
-- 1.3.6.1.4.1.2011.5.25.224.1.5
		-- 1.3.6.1.4.1.2011.5.25.224.1.6
		hwIPSecIkeProposalTable OBJECT-TYPE
			SYNTAX SEQUENCE OF HwIPSecIkeProposalEntry
			MAX-ACCESS not-accessible
			STATUS current
			DESCRIPTION
				"Description."
			::= { hwIPSecObjects 6 }
		
--   1.3.6.1.4.1.2011.5.25.224.1.5.1
-- 1.3.6.1.4.1.2011.5.25.224.1.5.1
		-- 1.3.6.1.4.1.2011.5.25.224.1.6.1
		hwIPSecIkeProposalEntry OBJECT-TYPE
			SYNTAX HwIPSecIkeProposalEntry
			MAX-ACCESS not-accessible
			STATUS current
			DESCRIPTION
				"Description."
			INDEX { hwIPSecIkeProposalNumber }
			::= { hwIPSecIkeProposalTable 1 }
		
		HwIPSecIkeProposalEntry ::=
			SEQUENCE { 
				hwIPSecIkeProposalNumber
					Integer32,
				hwIPSecIkeProposalAuthenmethod
					INTEGER,
				hwIPSecIkeProposalnAuthenAlgorithm
					INTEGER,
				hwIPSecIkeProposalIntegrityAlgorithm
					INTEGER,
				hwIPSecIkeProposalEncrypationAlgorithm
					INTEGER,
				hwIPSecIkeProposaldh
					INTEGER,
				hwIPSecIkeProposalSaDuration
					Integer32,
				hwIPSecIkeProposalReAuthentication
					Integer32,
				hwIPSecIkeProposalRowStatus
					RowStatus
			 }

--   1.3.6.1.4.1.2011.5.25.224.1.5.1.1
-- 1.3.6.1.4.1.2011.5.25.224.1.5.1.1
		-- 1.3.6.1.4.1.2011.5.25.224.1.6.1.1
		hwIPSecIkeProposalNumber OBJECT-TYPE
			SYNTAX Integer32 (1..100)
			MAX-ACCESS read-only
			STATUS current
			DESCRIPTION
				"Description."
			::= { hwIPSecIkeProposalEntry 1 }
		
--   1.3.6.1.4.1.2011.5.25.224.1.5.1.2
-- 1.3.6.1.4.1.2011.5.25.224.1.5.1.2
		-- 1.3.6.1.4.1.2011.5.25.224.1.6.1.2
		hwIPSecIkeProposalAuthenmethod OBJECT-TYPE
			SYNTAX INTEGER
				{
				preshare(1),
				rsasig(3)
				}
			MAX-ACCESS read-write
			STATUS current
			DESCRIPTION
				"Description."
			DEFVAL { preshare }
			::= { hwIPSecIkeProposalEntry 2 }
		
--   1.3.6.1.4.1.2011.5.25.224.1.5.1.3
-- 1.3.6.1.4.1.2011.5.25.224.1.5.1.3
		-- 1.3.6.1.4.1.2011.5.25.224.1.6.1.3
		hwIPSecIkeProposalnAuthenAlgorithm OBJECT-TYPE
			SYNTAX INTEGER
				{
				md5(1),
				sha1(2)
				}
			MAX-ACCESS read-write
			STATUS current
			DESCRIPTION
				"Description."
			DEFVAL { sha1 }
			::= { hwIPSecIkeProposalEntry 3 }
		
--   1.3.6.1.4.1.2011.5.25.224.1.5.1.4
-- 1.3.6.1.4.1.2011.5.25.224.1.5.1.4
		-- 1.3.6.1.4.1.2011.5.25.224.1.6.1.4
		hwIPSecIkeProposalIntegrityAlgorithm OBJECT-TYPE
			SYNTAX INTEGER
				{
				hmacmd596(1),
				hmacsha196(2),
				aesxcbc96(5)
				}
			MAX-ACCESS read-write
			STATUS current
			DESCRIPTION
				"Description."
			DEFVAL { hmacsha196 }
			::= { hwIPSecIkeProposalEntry 4 }
		
--   1.3.6.1.4.1.2011.5.25.224.1.5.1.5
-- 1.3.6.1.4.1.2011.5.25.224.1.5.1.5
		-- 1.3.6.1.4.1.2011.5.25.224.1.6.1.5
		hwIPSecIkeProposalEncrypationAlgorithm OBJECT-TYPE
			SYNTAX INTEGER
				{
				descbcno(0),
				descbc(1),
				des3cbc(5),
				aescbc128(128),
				aescbc192(192),
				aescbc256(256)
				}
			UNITS "value 128 192 256 is not real..descbcno is undo"
			MAX-ACCESS read-write
			STATUS current
			DESCRIPTION
				"Description."
			DEFVAL { descbc }
			::= { hwIPSecIkeProposalEntry 5 }
		
--   1.3.6.1.4.1.2011.5.25.224.1.5.1.6
-- 1.3.6.1.4.1.2011.5.25.224.1.5.1.6
		-- 1.3.6.1.4.1.2011.5.25.224.1.6.1.6
		hwIPSecIkeProposaldh OBJECT-TYPE
			SYNTAX INTEGER
				{
				group1(1),
				group2(2),
				group5(5)
				}
			MAX-ACCESS read-write
			STATUS current
			DESCRIPTION
				"Description."
			DEFVAL { group1 }
			::= { hwIPSecIkeProposalEntry 6 }
		
--   1.3.6.1.4.1.2011.5.25.224.1.5.1.7
-- 1.3.6.1.4.1.2011.5.25.224.1.5.1.7
		-- 1.3.6.1.4.1.2011.5.25.224.1.6.1.7
		hwIPSecIkeProposalSaDuration OBJECT-TYPE
			SYNTAX Integer32 (60..604800)
			UNITS "s"
			MAX-ACCESS read-write
			STATUS current
			DESCRIPTION
				"Description."
			DEFVAL { 86400 }
			::= { hwIPSecIkeProposalEntry 7 }
		
--   1.3.6.1.4.1.2011.5.25.224.1.5.1.8
-- 1.3.6.1.4.1.2011.5.25.224.1.5.1.8
		-- 1.3.6.1.4.1.2011.5.25.224.1.6.1.8
		hwIPSecIkeProposalReAuthentication OBJECT-TYPE
			SYNTAX Integer32 (0 | 60..604800)
			UNITS "s"
			MAX-ACCESS read-write
			STATUS current
			DESCRIPTION
				"Description."
			DEFVAL { 0 }
			::= { hwIPSecIkeProposalEntry 8 }
		
--   1.3.6.1.4.1.2011.5.25.224.1.5.1.9
-- 1.3.6.1.4.1.2011.5.25.224.1.5.1.9
		-- 1.3.6.1.4.1.2011.5.25.224.1.6.1.9
		hwIPSecIkeProposalRowStatus OBJECT-TYPE
			SYNTAX RowStatus
			MAX-ACCESS read-create
			STATUS current
			DESCRIPTION
				"Description."
			DEFVAL { active }
			::= { hwIPSecIkeProposalEntry 9 }
		
--   1.3.6.1.4.1.2011.5.25.224.1.6
-- 1.3.6.1.4.1.2011.5.25.224.1.6
		-- 1.3.6.1.4.1.2011.5.25.224.1.7
		hwIPSecIkePeerTable OBJECT-TYPE
			SYNTAX SEQUENCE OF HwIPSecIkePeerEntry
			MAX-ACCESS not-accessible
			STATUS current
			DESCRIPTION
				"Description."
			::= { hwIPSecObjects 7 }
		
--   1.3.6.1.4.1.2011.5.25.224.1.6.1
-- 1.3.6.1.4.1.2011.5.25.224.1.6.1
		-- 1.3.6.1.4.1.2011.5.25.224.1.7.1
		hwIPSecIkePeerEntry OBJECT-TYPE
			SYNTAX HwIPSecIkePeerEntry
			MAX-ACCESS not-accessible
			STATUS current
			DESCRIPTION
				"Description."
			INDEX { hwIPSecIkePeerName }
			::= { hwIPSecIkePeerTable 1 }
		
		HwIPSecIkePeerEntry ::=
			SEQUENCE { 
				hwIPSecIkePeerName
					OCTET STRING,
				hwIPSecIkePeerPresharedKeyEnable
					EnabledStatus,
				hwIPSecIkePeerPresharedKey
					OCTET STRING,
				hwIPSecIkePeerVpninstanceEnable
					EnabledStatus,
				hwIPSecIkePeerVpninstance
					OCTET STRING,
				hwIPSecIkePeerRemoteLowAddr
					IpAddress,
				hwIPSecIkePeerRemoteHighAddr
					IpAddress,
				hwIPSecIkePeerRemoteAuthAddr
					IpAddress,
				hwIPSecIkePeerRemoteAuthEndAddr
					IpAddress,
				hwIPSecIkePeerRemoteIppool
					Gauge32,
				hwIPSecIkePeerRemoteVpnInstance
					OCTET STRING,
				hwIPSecIkePeerRemoteNameEnable
					EnabledStatus,
				hwIPSecIkePeerRemoteName
					OCTET STRING,
				hwIPSecIkePeerExchangeMode
					INTEGER,
				hwIPSecIkePeerLocalIdtype
					INTEGER,
				hwIPSecIkePeerNatTraversal
					INTEGER,
				hwIPSecIkePeerProposalNum
					Integer32,
				hwIPSecIkePeerVersionName
					Integer32,
				hwIPSecIkePeerRowStatus
					RowStatus
			 }

--   1.3.6.1.4.1.2011.5.25.224.1.6.1.1
-- 1.3.6.1.4.1.2011.5.25.224.1.6.1.1
		-- 1.3.6.1.4.1.2011.5.25.224.1.7.1.1
		hwIPSecIkePeerName OBJECT-TYPE
			SYNTAX OCTET STRING (SIZE (0..15))
			MAX-ACCESS read-only
			STATUS current
			DESCRIPTION
				"Description."
			::= { hwIPSecIkePeerEntry 1 }
		
--   1.3.6.1.4.1.2011.5.25.224.1.6.1.2
-- 1.3.6.1.4.1.2011.5.25.224.1.6.1.2
		-- 1.3.6.1.4.1.2011.5.25.224.1.7.1.2
		hwIPSecIkePeerPresharedKeyEnable OBJECT-TYPE
			SYNTAX EnabledStatus
			MAX-ACCESS read-write
			STATUS current
			DESCRIPTION
				"Description."
			DEFVAL { disabled }
			::= { hwIPSecIkePeerEntry 2 }
		
--   1.3.6.1.4.1.2011.5.25.224.1.6.1.3
-- 1.3.6.1.4.1.2011.5.25.224.1.6.1.3
		-- 1.3.6.1.4.1.2011.5.25.224.1.7.1.3
		hwIPSecIkePeerPresharedKey OBJECT-TYPE
			SYNTAX OCTET STRING (SIZE (0..127))
			MAX-ACCESS read-write
			STATUS current
			DESCRIPTION
				"Description."
			::= { hwIPSecIkePeerEntry 3 }
		
--   1.3.6.1.4.1.2011.5.25.224.1.6.1.4
-- 1.3.6.1.4.1.2011.5.25.224.1.6.1.4
		-- 1.3.6.1.4.1.2011.5.25.224.1.7.1.4
		hwIPSecIkePeerVpninstanceEnable OBJECT-TYPE
			SYNTAX EnabledStatus
			MAX-ACCESS read-write
			STATUS current
			DESCRIPTION
				"Description."
			DEFVAL { disabled }
			::= { hwIPSecIkePeerEntry 4 }
		
--   1.3.6.1.4.1.2011.5.25.224.1.6.1.5
-- 1.3.6.1.4.1.2011.5.25.224.1.6.1.5
		-- 1.3.6.1.4.1.2011.5.25.224.1.7.1.5
		hwIPSecIkePeerVpninstance OBJECT-TYPE
			SYNTAX OCTET STRING (SIZE (0..31))
			MAX-ACCESS read-write
			STATUS current
			DESCRIPTION
				"Description."
			::= { hwIPSecIkePeerEntry 5 }
		
--   1.3.6.1.4.1.2011.5.25.224.1.6.1.6
-- 1.3.6.1.4.1.2011.5.25.224.1.6.1.6
		-- 1.3.6.1.4.1.2011.5.25.224.1.7.1.6
		hwIPSecIkePeerRemoteLowAddr OBJECT-TYPE
			SYNTAX IpAddress
			MAX-ACCESS read-write
			STATUS current
			DESCRIPTION
				"Description."
			::= { hwIPSecIkePeerEntry 6 }
		
--   1.3.6.1.4.1.2011.5.25.224.1.6.1.7
-- 1.3.6.1.4.1.2011.5.25.224.1.6.1.7
		-- 1.3.6.1.4.1.2011.5.25.224.1.7.1.7
		hwIPSecIkePeerRemoteHighAddr OBJECT-TYPE
			SYNTAX IpAddress
			MAX-ACCESS read-write
			STATUS current
			DESCRIPTION
				"Description."
			::= { hwIPSecIkePeerEntry 7 }
		
--   1.3.6.1.4.1.2011.5.25.224.1.6.1.8
-- 1.3.6.1.4.1.2011.5.25.224.1.6.1.8
		-- 1.3.6.1.4.1.2011.5.25.224.1.7.1.8
		hwIPSecIkePeerRemoteAuthAddr OBJECT-TYPE
			SYNTAX IpAddress
			MAX-ACCESS read-write
			STATUS current
			DESCRIPTION
				"Description."
			::= { hwIPSecIkePeerEntry 8 }
		
--   1.3.6.1.4.1.2011.5.25.224.1.6.1.9
-- 1.3.6.1.4.1.2011.5.25.224.1.6.1.9
		-- 1.3.6.1.4.1.2011.5.25.224.1.7.1.9
		hwIPSecIkePeerRemoteAuthEndAddr OBJECT-TYPE
			SYNTAX IpAddress
			MAX-ACCESS read-write
			STATUS current
			DESCRIPTION
				"Description."
			::= { hwIPSecIkePeerEntry 9 }
		
--   1.3.6.1.4.1.2011.5.25.224.1.6.1.10
-- 1.3.6.1.4.1.2011.5.25.224.1.6.1.10
		-- 1.3.6.1.4.1.2011.5.25.224.1.7.1.10
		hwIPSecIkePeerRemoteIppool OBJECT-TYPE
			SYNTAX Gauge32 (0..99 | 65535)
			MAX-ACCESS read-write
			STATUS current
			DESCRIPTION
				"Description."
			DEFVAL { 65535 }
			::= { hwIPSecIkePeerEntry 10 }
		
--   1.3.6.1.4.1.2011.5.25.224.1.6.1.11
-- 1.3.6.1.4.1.2011.5.25.224.1.6.1.11
		-- 1.3.6.1.4.1.2011.5.25.224.1.7.1.11
		hwIPSecIkePeerRemoteVpnInstance OBJECT-TYPE
			SYNTAX OCTET STRING (SIZE (0..31))
			MAX-ACCESS read-write
			STATUS current
			DESCRIPTION
				"Description."
			::= { hwIPSecIkePeerEntry 11 }
		
--   1.3.6.1.4.1.2011.5.25.224.1.6.1.12
-- 1.3.6.1.4.1.2011.5.25.224.1.6.1.12
		-- 1.3.6.1.4.1.2011.5.25.224.1.7.1.12
		hwIPSecIkePeerRemoteNameEnable OBJECT-TYPE
			SYNTAX EnabledStatus
			MAX-ACCESS read-write
			STATUS current
			DESCRIPTION
				"Description."
			DEFVAL { disabled }
			::= { hwIPSecIkePeerEntry 12 }
		
--   1.3.6.1.4.1.2011.5.25.224.1.6.1.13
-- 1.3.6.1.4.1.2011.5.25.224.1.6.1.13
		-- 1.3.6.1.4.1.2011.5.25.224.1.7.1.13
		hwIPSecIkePeerRemoteName OBJECT-TYPE
			SYNTAX OCTET STRING (SIZE (0..127))
			MAX-ACCESS read-write
			STATUS current
			DESCRIPTION
				"Description."
			::= { hwIPSecIkePeerEntry 13 }
		
--   1.3.6.1.4.1.2011.5.25.224.1.6.1.14
-- 1.3.6.1.4.1.2011.5.25.224.1.6.1.14
		-- 1.3.6.1.4.1.2011.5.25.224.1.7.1.14
		hwIPSecIkePeerExchangeMode OBJECT-TYPE
			SYNTAX INTEGER
				{
				main(2),
				aggressive(4)
				}
			MAX-ACCESS read-write
			STATUS current
			DESCRIPTION
				"Description."
			DEFVAL { main }
			::= { hwIPSecIkePeerEntry 14 }
		
--   1.3.6.1.4.1.2011.5.25.224.1.6.1.15
-- 1.3.6.1.4.1.2011.5.25.224.1.6.1.15
		-- 1.3.6.1.4.1.2011.5.25.224.1.7.1.15
		hwIPSecIkePeerLocalIdtype OBJECT-TYPE
			SYNTAX INTEGER
				{
				ip(1),
				fqdn(2),
				userfqdn(3),
				dn(9)
				}
			MAX-ACCESS read-write
			STATUS current
			DESCRIPTION
				"Description."
			DEFVAL { ip }
			::= { hwIPSecIkePeerEntry 15 }
		
--   1.3.6.1.4.1.2011.5.25.224.1.6.1.16
-- 1.3.6.1.4.1.2011.5.25.224.1.6.1.16
		-- 1.3.6.1.4.1.2011.5.25.224.1.7.1.16
		hwIPSecIkePeerNatTraversal OBJECT-TYPE
			SYNTAX INTEGER
				{
				notraversal(0),
				traversal(1)
				}
			MAX-ACCESS read-write
			STATUS current
			DESCRIPTION
				"Description."
			DEFVAL { 0 }
			::= { hwIPSecIkePeerEntry 16 }
		
--   1.3.6.1.4.1.2011.5.25.224.1.6.1.17
-- 1.3.6.1.4.1.2011.5.25.224.1.6.1.17
		-- 1.3.6.1.4.1.2011.5.25.224.1.7.1.17
		hwIPSecIkePeerProposalNum OBJECT-TYPE
			SYNTAX Integer32 (0..100)
			MAX-ACCESS read-write
			STATUS current
			DESCRIPTION
				"Description."
			::= { hwIPSecIkePeerEntry 17 }
		
--   1.3.6.1.4.1.2011.5.25.224.1.6.1.18
-- 1.3.6.1.4.1.2011.5.25.224.1.6.1.18
		-- 1.3.6.1.4.1.2011.5.25.224.1.7.1.18
		hwIPSecIkePeerVersionName OBJECT-TYPE
			SYNTAX Integer32 (1..3)
			MAX-ACCESS read-write
			STATUS current
			DESCRIPTION
				"Description."
			DEFVAL { 3 }
			::= { hwIPSecIkePeerEntry 18 }
		
--   1.3.6.1.4.1.2011.5.25.224.1.6.1.19
-- 1.3.6.1.4.1.2011.5.25.224.1.6.1.19
		-- 1.3.6.1.4.1.2011.5.25.224.1.7.1.19
		hwIPSecIkePeerRowStatus OBJECT-TYPE
			SYNTAX RowStatus
			MAX-ACCESS read-write
			STATUS current
			DESCRIPTION
				"Description."
			DEFVAL { active }
			::= { hwIPSecIkePeerEntry 19 }
		
--   1.3.6.1.4.1.2011.5.25.224.1.7
-- 1.3.6.1.4.1.2011.5.25.224.1.7
		-- 1.3.6.1.4.1.2011.5.25.224.1.8
		hwIPSecIkeDpdTable OBJECT-TYPE
			SYNTAX SEQUENCE OF HwIPSecIkeDpdEntry
			MAX-ACCESS not-accessible
			STATUS current
			DESCRIPTION
				"Description."
			::= { hwIPSecObjects 8 }
		
--   1.3.6.1.4.1.2011.5.25.224.1.7.1
-- 1.3.6.1.4.1.2011.5.25.224.1.7.1
		-- 1.3.6.1.4.1.2011.5.25.224.1.8.1
		hwIPSecIkeDpdEntry OBJECT-TYPE
			SYNTAX HwIPSecIkeDpdEntry
			MAX-ACCESS not-accessible
			STATUS current
			DESCRIPTION
				"Description."
			INDEX { hwIPSecIkeDpdIndex }
			::= { hwIPSecIkeDpdTable 1 }
		
		HwIPSecIkeDpdEntry ::=
			SEQUENCE { 
				hwIPSecIkeDpdIndex
					INTEGER,
				hwIPSecIkeDpdIntervalDemand
					INTEGER,
				hwIPSecIkeDpdCheckInterval
					Integer32,
				hwIPSecIkeDpdRetryInterval
					Integer32,
				hwIPSecIkeDpdRowStatus
					RowStatus
			 }

--   1.3.6.1.4.1.2011.5.25.224.1.7.1.1
-- 1.3.6.1.4.1.2011.5.25.224.1.7.1.1
		-- 1.3.6.1.4.1.2011.5.25.224.1.8.1.1
		hwIPSecIkeDpdIndex OBJECT-TYPE
			SYNTAX INTEGER { index(1) }
			MAX-ACCESS read-only
			STATUS current
			DESCRIPTION
				"Description."
			::= { hwIPSecIkeDpdEntry 1 }
		
--   1.3.6.1.4.1.2011.5.25.224.1.7.1.2
-- 1.3.6.1.4.1.2011.5.25.224.1.7.1.2
		-- 1.3.6.1.4.1.2011.5.25.224.1.8.1.2
		hwIPSecIkeDpdIntervalDemand OBJECT-TYPE
			SYNTAX INTEGER
				{
				interval(0),
				ondemand(1)
				}
			MAX-ACCESS read-write
			STATUS current
			DESCRIPTION
				"Description."
			DEFVAL { ondemand }
			::= { hwIPSecIkeDpdEntry 2 }
		
--   1.3.6.1.4.1.2011.5.25.224.1.7.1.3
-- 1.3.6.1.4.1.2011.5.25.224.1.7.1.3
		-- 1.3.6.1.4.1.2011.5.25.224.1.8.1.3
		hwIPSecIkeDpdCheckInterval OBJECT-TYPE
			SYNTAX Integer32 (0 | 10..3600)
			MAX-ACCESS read-write
			STATUS current
			DESCRIPTION
				"Description."
			DEFVAL { '0'b }
			::= { hwIPSecIkeDpdEntry 3 }
		
--   1.3.6.1.4.1.2011.5.25.224.1.7.1.4
-- 1.3.6.1.4.1.2011.5.25.224.1.7.1.4
		-- 1.3.6.1.4.1.2011.5.25.224.1.8.1.4
		hwIPSecIkeDpdRetryInterval OBJECT-TYPE
			SYNTAX Integer32 (2..60)
			MAX-ACCESS read-write
			STATUS current
			DESCRIPTION
				"Description."
			DEFVAL { 5 }
			::= { hwIPSecIkeDpdEntry 4 }
		
--   1.3.6.1.4.1.2011.5.25.224.1.7.1.5
-- 1.3.6.1.4.1.2011.5.25.224.1.7.1.5
		-- 1.3.6.1.4.1.2011.5.25.224.1.8.1.5
		hwIPSecIkeDpdRowStatus OBJECT-TYPE
			SYNTAX RowStatus
			MAX-ACCESS read-create
			STATUS current
			DESCRIPTION
				"Description."
			DEFVAL { active }
			::= { hwIPSecIkeDpdEntry 5 }
		
--   1.3.6.1.4.1.2011.5.25.224.1.8
-- 1.3.6.1.4.1.2011.5.25.224.1.8
		-- 1.3.6.1.4.1.2011.5.25.224.1.9
		hwIPSecSecProposalTable OBJECT-TYPE
			SYNTAX SEQUENCE OF HwIPSecSecProposalEntry
			MAX-ACCESS not-accessible
			STATUS current
			DESCRIPTION
				"Description."
			::= { hwIPSecObjects 9 }
		
--   1.3.6.1.4.1.2011.5.25.224.1.8.1
-- 1.3.6.1.4.1.2011.5.25.224.1.8.1
		-- 1.3.6.1.4.1.2011.5.25.224.1.9.1
		hwIPSecSecProposalEntry OBJECT-TYPE
			SYNTAX HwIPSecSecProposalEntry
			MAX-ACCESS not-accessible
			STATUS current
			DESCRIPTION
				"Description."
			INDEX { hwIPSecSecProposalName }
			::= { hwIPSecSecProposalTable 1 }
		
		HwIPSecSecProposalEntry ::=
			SEQUENCE { 
				hwIPSecSecProposalName
					OCTET STRING,
				hwIPSecSecProposalEncapmode
					INTEGER,
				hwIPSecSecProposalTransform
					INTEGER,
				hwIPSecSecProposalAhAuthenAlgorithm
					INTEGER,
				hwIPSecSecProposalEspauthenalgorithm
					INTEGER,
				hwIPSecSecProposalEspEncryptAlgorithm
					INTEGER,
				hwIPSecSecProposalRowStatus
					RowStatus
			 }

--   1.3.6.1.4.1.2011.5.25.224.1.8.1.1
-- 1.3.6.1.4.1.2011.5.25.224.1.8.1.1
		-- 1.3.6.1.4.1.2011.5.25.224.1.9.1.1
		hwIPSecSecProposalName OBJECT-TYPE
			SYNTAX OCTET STRING (SIZE (0..15))
			MAX-ACCESS read-only
			STATUS current
			DESCRIPTION
				"Description."
			::= { hwIPSecSecProposalEntry 1 }
		
--   1.3.6.1.4.1.2011.5.25.224.1.8.1.2
-- 1.3.6.1.4.1.2011.5.25.224.1.8.1.2
		-- 1.3.6.1.4.1.2011.5.25.224.1.9.1.2
		hwIPSecSecProposalEncapmode OBJECT-TYPE
			SYNTAX INTEGER
				{
				tunnel(0),
				transport(1)
				}
			MAX-ACCESS read-write
			STATUS current
			DESCRIPTION
				"Description."
			DEFVAL { tunnel }
			::= { hwIPSecSecProposalEntry 2 }
		
--   1.3.6.1.4.1.2011.5.25.224.1.8.1.3
-- 1.3.6.1.4.1.2011.5.25.224.1.8.1.3
		-- 1.3.6.1.4.1.2011.5.25.224.1.9.1.3
		hwIPSecSecProposalTransform OBJECT-TYPE
			SYNTAX INTEGER
				{
				ah(0),
				ahesp(1),
				esp(4)
				}
			MAX-ACCESS read-write
			STATUS current
			DESCRIPTION
				"Description."
			DEFVAL { esp }
			::= { hwIPSecSecProposalEntry 3 }
		
--   1.3.6.1.4.1.2011.5.25.224.1.8.1.4
-- 1.3.6.1.4.1.2011.5.25.224.1.8.1.4
		-- 1.3.6.1.4.1.2011.5.25.224.1.9.1.4
		hwIPSecSecProposalAhAuthenAlgorithm OBJECT-TYPE
			SYNTAX INTEGER
				{
				md5(0),
				sha1(1)
				}
			UNITS "not real value for enum"
			MAX-ACCESS read-write
			STATUS current
			DESCRIPTION
				"Description."
			DEFVAL { md5 }
			::= { hwIPSecSecProposalEntry 4 }
		
--   1.3.6.1.4.1.2011.5.25.224.1.8.1.5
-- 1.3.6.1.4.1.2011.5.25.224.1.8.1.5
		-- 1.3.6.1.4.1.2011.5.25.224.1.9.1.5
		hwIPSecSecProposalEspauthenalgorithm OBJECT-TYPE
			SYNTAX INTEGER
				{
				md5(0),
				sha1(1),
				no(2)
				}
			MAX-ACCESS read-write
			STATUS current
			DESCRIPTION
				"Description."
			DEFVAL { no }
			::= { hwIPSecSecProposalEntry 5 }
		
--   1.3.6.1.4.1.2011.5.25.224.1.8.1.6
-- 1.3.6.1.4.1.2011.5.25.224.1.8.1.6
		-- 1.3.6.1.4.1.2011.5.25.224.1.9.1.6
		hwIPSecSecProposalEspEncryptAlgorithm OBJECT-TYPE
			SYNTAX INTEGER
				{
				des3(0),
				des(1),
				aes(2),
				aes128(3),
				aes192(4),
				aes256(5),
				no(6)
				}
			MAX-ACCESS read-write
			STATUS current
			DESCRIPTION
				"Description."
			DEFVAL { no }
			::= { hwIPSecSecProposalEntry 6 }
		
--   1.3.6.1.4.1.2011.5.25.224.1.8.1.7
-- 1.3.6.1.4.1.2011.5.25.224.1.8.1.7
		-- 1.3.6.1.4.1.2011.5.25.224.1.9.1.7
		hwIPSecSecProposalRowStatus OBJECT-TYPE
			SYNTAX RowStatus
			MAX-ACCESS read-write
			STATUS current
			DESCRIPTION
				"Description."
			DEFVAL { active }
			::= { hwIPSecSecProposalEntry 7 }
		
--   1.3.6.1.4.1.2011.5.25.224.1.9
-- 1.3.6.1.4.1.2011.5.25.224.1.9
		-- 1.3.6.1.4.1.2011.5.25.224.1.10
		hwIPSecSecPolicyIsakmpTable OBJECT-TYPE
			SYNTAX SEQUENCE OF HwIPSecSecPolicyIsakmpEntry
			MAX-ACCESS not-accessible
			STATUS current
			DESCRIPTION
				"Description."
			::= { hwIPSecObjects 10 }
		
--   1.3.6.1.4.1.2011.5.25.224.1.9.1
-- 1.3.6.1.4.1.2011.5.25.224.1.9.1
		-- 1.3.6.1.4.1.2011.5.25.224.1.10.1
		hwIPSecSecPolicyIsakmpEntry OBJECT-TYPE
			SYNTAX HwIPSecSecPolicyIsakmpEntry
			MAX-ACCESS not-accessible
			STATUS current
			DESCRIPTION
				"Description."
			INDEX { hwIPSecSecPolicyIsakmpOrTemp, hwIPSecSecPolicyIsakmpName, hwIPSecSecPolicyIsakmpSeqNumber }
			::= { hwIPSecSecPolicyIsakmpTable 1 }
		
		HwIPSecSecPolicyIsakmpEntry ::=
			SEQUENCE { 
				hwIPSecSecPolicyIsakmpOrTemp
					INTEGER,
				hwIPSecSecPolicyIsakmpName
					OCTET STRING,
				hwIPSecSecPolicyIsakmpSeqNumber
					Integer32,
				hwIPSecSecPolicyIsakmpSecurAclNumber
					Integer32,
				hwIPSecSecPolicyIsakmpProposalNameEnable
					EnabledStatus,
				hwIPSecSecPolicyIsakmpProposalName
					OCTET STRING,
				hwIPSecSecPolicyIsakmpFragmentBfEncrypt
					Integer32,
				hwIPSecSecPolicyIsakmpDfBit
					Integer32,
				hwIPSecSecPolicyIsakmpSpdLimitInbnd
					Integer32,
				hwIPSecSecPolicyIsakmpSpdLimitOutbnd
					Integer32,
				hwIPSecSecPolicyIsakmpSetDscpInEnable
					EnabledStatus,
				hwIPSecSecPolicyIsakmpDscpInbnd
					Integer32,
				hwIPSecSecPolicyIsakmpSetDscpOutEnable
					EnabledStatus,
				hwIPSecSecPolicyIsakmpDscpOutbnd
					Integer32,
				hwIPSecSecPolicyIsakmpIkePeernameEnable
					EnabledStatus,
				hwIPSecSecPolicyIsakmpIkePeername
					OCTET STRING,
				hwIPSecSecPolicyIsakmpLocaladdressEnable
					EnabledStatus,
				hwIPSecSecPolicyIsakmpLocaladdress
					IpAddress,
				hwIPSecSecPolicyIsakmpPfs
					INTEGER,
				hwIPSecSecPolicyIsakmpTrafficBased
					Integer32,
				hwIPSecSecPolicyIsakmpTimeBased
					Integer32,
				hwIPSecSecPolicyIsakmpLogEnable
					EnabledStatus,
				hwIPSecSecPolicyIsakmpRowStatus
					RowStatus
			 }

--   1.3.6.1.4.1.2011.5.25.224.1.9.1.1
-- 1.3.6.1.4.1.2011.5.25.224.1.9.1.1
		-- 1.3.6.1.4.1.2011.5.25.224.1.10.1.1
		hwIPSecSecPolicyIsakmpOrTemp OBJECT-TYPE
			SYNTAX INTEGER
				{
				temp(1),
				notemp(2)
				}
			MAX-ACCESS read-only
			STATUS current
			DESCRIPTION
				"Description."
			::= { hwIPSecSecPolicyIsakmpEntry 1 }
		
--   1.3.6.1.4.1.2011.5.25.224.1.9.1.2
-- 1.3.6.1.4.1.2011.5.25.224.1.9.1.2
		-- 1.3.6.1.4.1.2011.5.25.224.1.10.1.2
		hwIPSecSecPolicyIsakmpName OBJECT-TYPE
			SYNTAX OCTET STRING (SIZE (0..15))
			MAX-ACCESS read-only
			STATUS current
			DESCRIPTION
				"Description."
			::= { hwIPSecSecPolicyIsakmpEntry 2 }
		
--   1.3.6.1.4.1.2011.5.25.224.1.9.1.3
-- 1.3.6.1.4.1.2011.5.25.224.1.9.1.3
		-- 1.3.6.1.4.1.2011.5.25.224.1.10.1.3
		hwIPSecSecPolicyIsakmpSeqNumber OBJECT-TYPE
			SYNTAX Integer32 (1..10000)
			MAX-ACCESS read-only
			STATUS current
			DESCRIPTION
				"Description."
			::= { hwIPSecSecPolicyIsakmpEntry 3 }
		
--   1.3.6.1.4.1.2011.5.25.224.1.9.1.4
-- 1.3.6.1.4.1.2011.5.25.224.1.9.1.4
		-- 1.3.6.1.4.1.2011.5.25.224.1.10.1.4
		hwIPSecSecPolicyIsakmpSecurAclNumber OBJECT-TYPE
			SYNTAX Integer32 (0 | 3000..3999)
			MAX-ACCESS read-write
			STATUS current
			DESCRIPTION
				"Description."
			::= { hwIPSecSecPolicyIsakmpEntry 4 }
		
--   1.3.6.1.4.1.2011.5.25.224.1.9.1.5
-- 1.3.6.1.4.1.2011.5.25.224.1.9.1.5
		-- 1.3.6.1.4.1.2011.5.25.224.1.10.1.5
		hwIPSecSecPolicyIsakmpProposalNameEnable OBJECT-TYPE
			SYNTAX EnabledStatus
			MAX-ACCESS read-write
			STATUS current
			DESCRIPTION
				"Description."
			DEFVAL { disabled }
			::= { hwIPSecSecPolicyIsakmpEntry 5 }
		
--   1.3.6.1.4.1.2011.5.25.224.1.9.1.6
-- 1.3.6.1.4.1.2011.5.25.224.1.9.1.6
		-- 1.3.6.1.4.1.2011.5.25.224.1.10.1.6
		hwIPSecSecPolicyIsakmpProposalName OBJECT-TYPE
			SYNTAX OCTET STRING (SIZE (0..256))
			MAX-ACCESS read-write
			STATUS current
			DESCRIPTION
				"Description."
			::= { hwIPSecSecPolicyIsakmpEntry 6 }
		
--   1.3.6.1.4.1.2011.5.25.224.1.9.1.7
-- 1.3.6.1.4.1.2011.5.25.224.1.9.1.7
		-- 1.3.6.1.4.1.2011.5.25.224.1.10.1.7
		hwIPSecSecPolicyIsakmpFragmentBfEncrypt OBJECT-TYPE
			SYNTAX Integer32 (0..1)
			MAX-ACCESS read-write
			STATUS current
			DESCRIPTION
				"Description."
			::= { hwIPSecSecPolicyIsakmpEntry 7 }
		
--   1.3.6.1.4.1.2011.5.25.224.1.9.1.8
-- 1.3.6.1.4.1.2011.5.25.224.1.9.1.8
		-- 1.3.6.1.4.1.2011.5.25.224.1.10.1.8
		hwIPSecSecPolicyIsakmpDfBit OBJECT-TYPE
			SYNTAX Integer32 (0..1)
			MAX-ACCESS read-write
			STATUS current
			DESCRIPTION
				"Description."
			::= { hwIPSecSecPolicyIsakmpEntry 8 }
		
--   1.3.6.1.4.1.2011.5.25.224.1.9.1.9
-- 1.3.6.1.4.1.2011.5.25.224.1.9.1.9
		-- 1.3.6.1.4.1.2011.5.25.224.1.10.1.9
		hwIPSecSecPolicyIsakmpSpdLimitInbnd OBJECT-TYPE
			SYNTAX Integer32 (0 | 8..4194303)
			UNITS "kbytes/s"
			MAX-ACCESS read-write
			STATUS current
			DESCRIPTION
				"Description."
			::= { hwIPSecSecPolicyIsakmpEntry 9 }
		
--   1.3.6.1.4.1.2011.5.25.224.1.9.1.10
-- 1.3.6.1.4.1.2011.5.25.224.1.9.1.10
		-- 1.3.6.1.4.1.2011.5.25.224.1.10.1.10
		hwIPSecSecPolicyIsakmpSpdLimitOutbnd OBJECT-TYPE
			SYNTAX Integer32 (0 | 8..4194303)
			UNITS "kbytes/s"
			MAX-ACCESS read-write
			STATUS current
			DESCRIPTION
				"Description."
			::= { hwIPSecSecPolicyIsakmpEntry 10 }
		
--   1.3.6.1.4.1.2011.5.25.224.1.9.1.11
-- 1.3.6.1.4.1.2011.5.25.224.1.9.1.11
		-- 1.3.6.1.4.1.2011.5.25.224.1.10.1.11
		hwIPSecSecPolicyIsakmpSetDscpInEnable OBJECT-TYPE
			SYNTAX EnabledStatus
			MAX-ACCESS read-write
			STATUS current
			DESCRIPTION
				"Description."
			DEFVAL { disabled }
			::= { hwIPSecSecPolicyIsakmpEntry 11 }
		
--   1.3.6.1.4.1.2011.5.25.224.1.9.1.12
-- 1.3.6.1.4.1.2011.5.25.224.1.9.1.12
		-- 1.3.6.1.4.1.2011.5.25.224.1.10.1.12
		hwIPSecSecPolicyIsakmpDscpInbnd OBJECT-TYPE
			SYNTAX Integer32 (0..63)
			MAX-ACCESS read-write
			STATUS current
			DESCRIPTION
				"Description."
			::= { hwIPSecSecPolicyIsakmpEntry 12 }
		
--   1.3.6.1.4.1.2011.5.25.224.1.9.1.13
-- 1.3.6.1.4.1.2011.5.25.224.1.9.1.13
		-- 1.3.6.1.4.1.2011.5.25.224.1.10.1.13
		hwIPSecSecPolicyIsakmpSetDscpOutEnable OBJECT-TYPE
			SYNTAX EnabledStatus
			MAX-ACCESS read-write
			STATUS current
			DESCRIPTION
				"Description."
			DEFVAL { disabled }
			::= { hwIPSecSecPolicyIsakmpEntry 13 }
		
--   1.3.6.1.4.1.2011.5.25.224.1.9.1.14
-- 1.3.6.1.4.1.2011.5.25.224.1.9.1.14
		-- 1.3.6.1.4.1.2011.5.25.224.1.10.1.14
		hwIPSecSecPolicyIsakmpDscpOutbnd OBJECT-TYPE
			SYNTAX Integer32 (0..63)
			MAX-ACCESS read-write
			STATUS current
			DESCRIPTION
				"Description."
			::= { hwIPSecSecPolicyIsakmpEntry 14 }
		
--   1.3.6.1.4.1.2011.5.25.224.1.9.1.15
-- 1.3.6.1.4.1.2011.5.25.224.1.9.1.15
		-- 1.3.6.1.4.1.2011.5.25.224.1.10.1.15
		hwIPSecSecPolicyIsakmpIkePeernameEnable OBJECT-TYPE
			SYNTAX EnabledStatus
			MAX-ACCESS read-write
			STATUS current
			DESCRIPTION
				"Description."
			DEFVAL { disabled }
			::= { hwIPSecSecPolicyIsakmpEntry 15 }
		
--   1.3.6.1.4.1.2011.5.25.224.1.9.1.16
-- 1.3.6.1.4.1.2011.5.25.224.1.9.1.16
		-- 1.3.6.1.4.1.2011.5.25.224.1.10.1.16
		hwIPSecSecPolicyIsakmpIkePeername OBJECT-TYPE
			SYNTAX OCTET STRING (SIZE (0..15))
			MAX-ACCESS read-write
			STATUS current
			DESCRIPTION
				"Description."
			::= { hwIPSecSecPolicyIsakmpEntry 16 }
		
--   1.3.6.1.4.1.2011.5.25.224.1.9.1.17
-- 1.3.6.1.4.1.2011.5.25.224.1.9.1.17
		-- 1.3.6.1.4.1.2011.5.25.224.1.10.1.17
		hwIPSecSecPolicyIsakmpLocaladdressEnable OBJECT-TYPE
			SYNTAX EnabledStatus
			MAX-ACCESS read-write
			STATUS current
			DESCRIPTION
				"Description."
			DEFVAL { disabled }
			::= { hwIPSecSecPolicyIsakmpEntry 17 }
		
--   1.3.6.1.4.1.2011.5.25.224.1.9.1.18
-- 1.3.6.1.4.1.2011.5.25.224.1.9.1.18
		-- 1.3.6.1.4.1.2011.5.25.224.1.10.1.18
		hwIPSecSecPolicyIsakmpLocaladdress OBJECT-TYPE
			SYNTAX IpAddress
			MAX-ACCESS read-write
			STATUS current
			DESCRIPTION
				"Description."
			::= { hwIPSecSecPolicyIsakmpEntry 18 }
		
--   1.3.6.1.4.1.2011.5.25.224.1.9.1.19
-- 1.3.6.1.4.1.2011.5.25.224.1.9.1.19
		-- 1.3.6.1.4.1.2011.5.25.224.1.10.1.19
		hwIPSecSecPolicyIsakmpPfs OBJECT-TYPE
			SYNTAX INTEGER
				{
				no(0),
				dhgroup1(1),
				dhgroup2(2),
				dhgroup5(5)
				}
			MAX-ACCESS read-write
			STATUS current
			DESCRIPTION
				"Description."
			::= { hwIPSecSecPolicyIsakmpEntry 19 }
		
--   1.3.6.1.4.1.2011.5.25.224.1.9.1.20
-- 1.3.6.1.4.1.2011.5.25.224.1.9.1.20
		-- 1.3.6.1.4.1.2011.5.25.224.1.10.1.20
		hwIPSecSecPolicyIsakmpTrafficBased OBJECT-TYPE
			SYNTAX Integer32 (0 | 8000..200000000)
			MAX-ACCESS read-write
			STATUS current
			DESCRIPTION
				"Description."
			::= { hwIPSecSecPolicyIsakmpEntry 20 }
		
--   1.3.6.1.4.1.2011.5.25.224.1.9.1.21
-- 1.3.6.1.4.1.2011.5.25.224.1.9.1.21
		-- 1.3.6.1.4.1.2011.5.25.224.1.10.1.21
		hwIPSecSecPolicyIsakmpTimeBased OBJECT-TYPE
			SYNTAX Integer32 (0 | 480..604800)
			MAX-ACCESS read-write
			STATUS current
			DESCRIPTION
				"Description."
			::= { hwIPSecSecPolicyIsakmpEntry 21 }
		
--   1.3.6.1.4.1.2011.5.25.224.1.9.1.22
-- 1.3.6.1.4.1.2011.5.25.224.1.9.1.22
		-- 1.3.6.1.4.1.2011.5.25.224.1.10.1.22
		hwIPSecSecPolicyIsakmpLogEnable OBJECT-TYPE
			SYNTAX EnabledStatus
			MAX-ACCESS read-write
			STATUS current
			DESCRIPTION
				"Description."
			DEFVAL { disabled }
			::= { hwIPSecSecPolicyIsakmpEntry 22 }
		
--   1.3.6.1.4.1.2011.5.25.224.1.9.1.23
-- 1.3.6.1.4.1.2011.5.25.224.1.9.1.23
		-- 1.3.6.1.4.1.2011.5.25.224.1.10.1.23
		hwIPSecSecPolicyIsakmpRowStatus OBJECT-TYPE
			SYNTAX RowStatus
			MAX-ACCESS read-create
			STATUS current
			DESCRIPTION
				"Description."
			DEFVAL { active }
			::= { hwIPSecSecPolicyIsakmpEntry 23 }
		
--   1.3.6.1.4.1.2011.5.25.224.1.10
-- 1.3.6.1.4.1.2011.5.25.224.1.10
		-- 1.3.6.1.4.1.2011.5.25.224.1.11
		hwIPSecSecPolicyIsakmpTempTable OBJECT-TYPE
			SYNTAX SEQUENCE OF HwIPSecSecPolicyIsakmpTempEntry
			MAX-ACCESS not-accessible
			STATUS current
			DESCRIPTION
				"Description."
			::= { hwIPSecObjects 11 }
		
--   1.3.6.1.4.1.2011.5.25.224.1.11.1
-- 1.3.6.1.4.1.2011.5.25.224.1.10.1
		-- 1.3.6.1.4.1.2011.5.25.224.1.11.1
		hwIPSecSecPolicyIsakmpTempEntry OBJECT-TYPE
			SYNTAX HwIPSecSecPolicyIsakmpTempEntry
			MAX-ACCESS not-accessible
			STATUS current
			DESCRIPTION
				"Description."
			INDEX { hwIPSecSecPolicyIsakmpTempIsakmpName, hwIPSecSecPolicyIsakmpTempIsakmpSeqNumber, hwIPSecSecPolicyIsakmpTempTemplateName }
			::= { hwIPSecSecPolicyIsakmpTempTable 1 }
		
		HwIPSecSecPolicyIsakmpTempEntry ::=
			SEQUENCE { 
				hwIPSecSecPolicyIsakmpTempIsakmpName
					OCTET STRING,
				hwIPSecSecPolicyIsakmpTempIsakmpSeqNumber
					Integer32,
				hwIPSecSecPolicyIsakmpTempTemplateName
					OCTET STRING,
				hwIPSecSecPolicyIsakmpTempRowStatus
					RowStatus
			 }

--   1.3.6.1.4.1.2011.5.25.224.1.10.1.1
-- 1.3.6.1.4.1.2011.5.25.224.1.10.1.1
		-- 1.3.6.1.4.1.2011.5.25.224.1.11.1.1
		hwIPSecSecPolicyIsakmpTempIsakmpName OBJECT-TYPE
			SYNTAX OCTET STRING (SIZE (0..15))
			MAX-ACCESS read-only
			STATUS current
			DESCRIPTION
				"Description."
			::= { hwIPSecSecPolicyIsakmpTempEntry 1 }
		
--   1.3.6.1.4.1.2011.5.25.224.1.10.1.2
-- 1.3.6.1.4.1.2011.5.25.224.1.10.1.2
		-- 1.3.6.1.4.1.2011.5.25.224.1.11.1.2
		hwIPSecSecPolicyIsakmpTempIsakmpSeqNumber OBJECT-TYPE
			SYNTAX Integer32 (1..10000)
			MAX-ACCESS read-only
			STATUS current
			DESCRIPTION
				"Description."
			::= { hwIPSecSecPolicyIsakmpTempEntry 2 }
		
--   1.3.6.1.4.1.2011.5.25.224.1.10.1.3
-- 1.3.6.1.4.1.2011.5.25.224.1.10.1.3
		-- 1.3.6.1.4.1.2011.5.25.224.1.11.1.3
		hwIPSecSecPolicyIsakmpTempTemplateName OBJECT-TYPE
			SYNTAX OCTET STRING (SIZE (0..15))
			MAX-ACCESS read-only
			STATUS current
			DESCRIPTION
				"Description."
			::= { hwIPSecSecPolicyIsakmpTempEntry 3 }
		
--   1.3.6.1.4.1.2011.5.25.224.1.10.1.4
-- 1.3.6.1.4.1.2011.5.25.224.1.10.1.4
		-- 1.3.6.1.4.1.2011.5.25.224.1.11.1.4
		hwIPSecSecPolicyIsakmpTempRowStatus OBJECT-TYPE
			SYNTAX RowStatus
			MAX-ACCESS read-create
			STATUS current
			DESCRIPTION
				"Description."
			DEFVAL { active }
			::= { hwIPSecSecPolicyIsakmpTempEntry 4 }
		
--   1.3.6.1.4.1.2011.5.25.224.1.11
-- 1.3.6.1.4.1.2011.5.25.224.1.11
		-- 1.3.6.1.4.1.2011.5.25.224.1.12
		hwIPSecSecTunnelTable OBJECT-TYPE
			SYNTAX SEQUENCE OF HwIPSecSecTunnelEntry
			MAX-ACCESS not-accessible
			STATUS current
			DESCRIPTION
				"Description."
			::= { hwIPSecObjects 12 }
		
--   1.3.6.1.4.1.2011.5.25.224.1.12.1
-- 1.3.6.1.4.1.2011.5.25.224.1.11.1
		-- 1.3.6.1.4.1.2011.5.25.224.1.12.1
		hwIPSecSecTunnelEntry OBJECT-TYPE
			SYNTAX HwIPSecSecTunnelEntry
			MAX-ACCESS not-accessible
			STATUS current
			DESCRIPTION
				"Description."
			INDEX { hwIPSecSecTunnelName }
			::= { hwIPSecSecTunnelTable 1 }
		
		HwIPSecSecTunnelEntry ::=
			SEQUENCE { 
				hwIPSecSecTunnelName
					OCTET STRING,
				hwIPSecSecTunnelPolicynameEanble
					EnabledStatus,
				hwIPSecSecTunnelPolicyname
					OCTET STRING,
				hwIPSecSecTunnelImportFilterPolicy
					Integer32,
				hwIPSecSecTunnelOutportFilterPolicy
					Integer32,
				hwIPSecUndoServiceRoute
					Integer32,
				hwIPSecPortMirrorInEnable
					Integer32,
				hwIPSecPortMirrorOutEnable
					Integer32,
				hwIPSecPortMirrorInAcl
					Integer32,
				hwIPSecPortMirrorOutAcl
					Integer32,
				hwIPSecPortObserverIndex
					Integer32,
				hwIPSecSecTunnelRowStatus
					RowStatus,
				hwIPSecSecTunnelInstanceId
					Integer32
			 }

--   1.3.6.1.4.1.2011.5.25.224.1.12.1.1
-- 1.3.6.1.4.1.2011.5.25.224.1.11.1.1
		-- 1.3.6.1.4.1.2011.5.25.224.1.12.1.1
		hwIPSecSecTunnelName OBJECT-TYPE
			SYNTAX OCTET STRING (SIZE (0..47))
			MAX-ACCESS read-only
			STATUS current
			DESCRIPTION
				"Description."
			::= { hwIPSecSecTunnelEntry 1 }
		
--   1.3.6.1.4.1.2011.5.25.224.1.12.1.2
-- 1.3.6.1.4.1.2011.5.25.224.1.11.1.2
		-- 1.3.6.1.4.1.2011.5.25.224.1.12.1.2
		hwIPSecSecTunnelPolicynameEanble OBJECT-TYPE
			SYNTAX EnabledStatus
			MAX-ACCESS read-write
			STATUS current
			DESCRIPTION
				"Description."
			DEFVAL { disabled }
			::= { hwIPSecSecTunnelEntry 2 }
		
--   1.3.6.1.4.1.2011.5.25.224.1.12.1.3
-- 1.3.6.1.4.1.2011.5.25.224.1.11.1.3
		-- 1.3.6.1.4.1.2011.5.25.224.1.12.1.3
		hwIPSecSecTunnelPolicyname OBJECT-TYPE
			SYNTAX OCTET STRING (SIZE (0..15))
			MAX-ACCESS read-write
			STATUS current
			DESCRIPTION
				"Description."
			::= { hwIPSecSecTunnelEntry 3 }
		
--   1.3.6.1.4.1.2011.5.25.224.1.12.1.4
-- 1.3.6.1.4.1.2011.5.25.224.1.11.1.4
		-- 1.3.6.1.4.1.2011.5.25.224.1.12.1.4
		hwIPSecSecTunnelImportFilterPolicy OBJECT-TYPE
			SYNTAX Integer32 (0 | 3000..3999)
			MAX-ACCESS read-write
			STATUS current
			DESCRIPTION
				"Description."
			::= { hwIPSecSecTunnelEntry 4 }
		
--   1.3.6.1.4.1.2011.5.25.224.1.12.1.5
-- 1.3.6.1.4.1.2011.5.25.224.1.11.1.5
		-- 1.3.6.1.4.1.2011.5.25.224.1.12.1.5
		hwIPSecSecTunnelOutportFilterPolicy OBJECT-TYPE
			SYNTAX Integer32 (0 | 3000..3999)
			MAX-ACCESS read-write
			STATUS current
			DESCRIPTION
				"Description."
			::= { hwIPSecSecTunnelEntry 5 }
		
--   1.3.6.1.4.1.2011.5.25.224.1.10.1.4
-- 1.3.6.1.4.1.2011.5.25.224.1.10.1.4
		-- 1.3.6.1.4.1.2011.5.25.224.1.12.1.6
		hwIPSecUndoServiceRoute OBJECT-TYPE
			SYNTAX Integer32 (0..1)
			MAX-ACCESS read-write
			STATUS current
			DESCRIPTION
				"Description."
			::= { hwIPSecSecTunnelEntry 6 }
		
--   1.3.6.1.4.1.2011.5.25.224.1.10.1.4
-- 1.3.6.1.4.1.2011.5.25.224.1.10.1.4
		-- 1.3.6.1.4.1.2011.5.25.224.1.12.1.7
		hwIPSecPortMirrorInEnable OBJECT-TYPE
			SYNTAX Integer32 (0..1)
			MAX-ACCESS read-write
			STATUS current
			DESCRIPTION
				"Description."
			::= { hwIPSecSecTunnelEntry 7 }
		
--   1.3.6.1.4.1.2011.5.25.224.1.10.1.4
-- 1.3.6.1.4.1.2011.5.25.224.1.10.1.4
		-- 1.3.6.1.4.1.2011.5.25.224.1.12.1.8
		hwIPSecPortMirrorOutEnable OBJECT-TYPE
			SYNTAX Integer32 (0..1)
			MAX-ACCESS read-write
			STATUS current
			DESCRIPTION
				"Description."
			::= { hwIPSecSecTunnelEntry 8 }
		
--   1.3.6.1.4.1.2011.5.25.224.1.10.1.4
-- 1.3.6.1.4.1.2011.5.25.224.1.10.1.4
		-- 1.3.6.1.4.1.2011.5.25.224.1.12.1.9
		hwIPSecPortMirrorInAcl OBJECT-TYPE
			SYNTAX Integer32 (0 | 3000..3999)
			MAX-ACCESS read-write
			STATUS current
			DESCRIPTION
				"Description."
			::= { hwIPSecSecTunnelEntry 9 }
		
--   1.3.6.1.4.1.2011.5.25.224.1.10.1.4
-- 1.3.6.1.4.1.2011.5.25.224.1.10.1.4
		-- 1.3.6.1.4.1.2011.5.25.224.1.12.1.10
		hwIPSecPortMirrorOutAcl OBJECT-TYPE
			SYNTAX Integer32 (0 | 3000..3999)
			MAX-ACCESS read-write
			STATUS current
			DESCRIPTION
				"Description."
			::= { hwIPSecSecTunnelEntry 10 }
		
--   1.3.6.1.4.1.2011.5.25.224.1.10.1.4
-- 1.3.6.1.4.1.2011.5.25.224.1.10.1.4
		-- 1.3.6.1.4.1.2011.5.25.224.1.12.1.11
		hwIPSecPortObserverIndex OBJECT-TYPE
			SYNTAX Integer32 (0 | 1..255)
			MAX-ACCESS read-write
			STATUS current
			DESCRIPTION
				"Description."
			::= { hwIPSecSecTunnelEntry 11 }
		
		-- 1.3.6.1.4.1.2011.5.25.224.1.12.1.12
		hwIPSecSecTunnelRowStatus OBJECT-TYPE
			SYNTAX RowStatus
			MAX-ACCESS read-create
			STATUS current
			DESCRIPTION
				"Description."
			DEFVAL { active }
			::= { hwIPSecSecTunnelEntry 12 }

		

		-- 1.3.6.1.4.1.2011.5.25.224.1.12.1.13

		hwIPSecSecTunnelInstanceId OBJECT-TYPE
			SYNTAX Integer32 (0..8)
			MAX-ACCESS read-write
			STATUS current
			DESCRIPTION
				"Description."
			::= { hwIPSecSecTunnelEntry 13 }		
--  1.3.6.1.4.1.2011.5.25.224.1.12
		-- 1.3.6.1.4.1.2011.5.25.224.1.13
		hwIPSecPkiEntityTable OBJECT-TYPE
			SYNTAX SEQUENCE OF HwIPSecPkiEntityEntry
			MAX-ACCESS not-accessible
			STATUS current
			DESCRIPTION
				"Description."
			::= { hwIPSecObjects 13 }
		
--  1.3.6.1.4.1.2011.5.25.224.1.12.1
		-- 1.3.6.1.4.1.2011.5.25.224.1.13.1
		hwIPSecPkiEntityEntry OBJECT-TYPE
			SYNTAX HwIPSecPkiEntityEntry
			MAX-ACCESS not-accessible
			STATUS current
			DESCRIPTION
				"Description."
			INDEX { hwIPSecPkiEntityName }
			::= { hwIPSecPkiEntityTable 1 }
		
		HwIPSecPkiEntityEntry ::=
			SEQUENCE { 
				hwIPSecPkiEntityName
					OCTET STRING,
				hwIPSecPkiEntityCmmNameEnable
					EnabledStatus,
				hwIPSecPkiEntityCmmName
					OCTET STRING,
				hwIPSecPkiEntityCountryEnable
					EnabledStatus,
				hwIPSecPkiEntityCountry
					OCTET STRING,
				hwIPSecPkiEntityEmailEnable
					EnabledStatus,
				hwIPSecPkiEntityEmail
					OCTET STRING,
				hwIPSecPkiEntityFqdnEnable
					EnabledStatus,
				hwIPSecPkiEntityFqdn
					OCTET STRING,
				hwIPSecPkiEntityIpAddrEnable
					EnabledStatus,
				hwIPSecPkiEntityIpAddr
					IpAddress,
				hwIPSecPkiEntityLocalityEnable
					EnabledStatus,
				hwIPSecPkiEntityLocality
					OCTET STRING,
				hwIPSecPkiEntityOrgEnable
					EnabledStatus,
				hwIPSecPkiEntityOrg
					OCTET STRING,
				hwIPSecPkiEntityOrgUnitEnable
					EnabledStatus,
				hwIPSecPkiEntityOrgUnit
					OCTET STRING,
				hwIPSecPkiEntityStateEnable
					EnabledStatus,
				hwIPSecPkiEntityState
					OCTET STRING,
				hwIPSecPkiEntityRowStatus
					RowStatus
			 }

--  1.3.6.1.4.1.2011.5.25.224.1.12.1.1
		-- 1.3.6.1.4.1.2011.5.25.224.1.13.1.1
		hwIPSecPkiEntityName OBJECT-TYPE
			SYNTAX OCTET STRING (SIZE (0..31))
			MAX-ACCESS read-only
			STATUS current
			DESCRIPTION
				"Description."
			::= { hwIPSecPkiEntityEntry 1 }
		
--  1.3.6.1.4.1.2011.5.25.224.1.12.1.2
		-- 1.3.6.1.4.1.2011.5.25.224.1.13.1.2
		hwIPSecPkiEntityCmmNameEnable OBJECT-TYPE
			SYNTAX EnabledStatus
			MAX-ACCESS read-write
			STATUS current
			DESCRIPTION
				"Description."
			DEFVAL { disabled }
			::= { hwIPSecPkiEntityEntry 2 }
		
--  1.3.6.1.4.1.2011.5.25.224.1.12.1.3
		-- 1.3.6.1.4.1.2011.5.25.224.1.13.1.3
		hwIPSecPkiEntityCmmName OBJECT-TYPE
			SYNTAX OCTET STRING (SIZE (0..31))
			MAX-ACCESS read-write
			STATUS current
			DESCRIPTION
				"Description."
			::= { hwIPSecPkiEntityEntry 3 }
		
--  1.3.6.1.4.1.2011.5.25.224.1.12.1.4
		-- 1.3.6.1.4.1.2011.5.25.224.1.13.1.4
		hwIPSecPkiEntityCountryEnable OBJECT-TYPE
			SYNTAX EnabledStatus
			MAX-ACCESS read-write
			STATUS current
			DESCRIPTION
				"Description."
			DEFVAL { disabled }
			::= { hwIPSecPkiEntityEntry 4 }
		
--  1.3.6.1.4.1.2011.5.25.224.1.12.1.5
		-- 1.3.6.1.4.1.2011.5.25.224.1.13.1.5
		hwIPSecPkiEntityCountry OBJECT-TYPE
			SYNTAX OCTET STRING (SIZE (0..2))
			MAX-ACCESS read-write
			STATUS current
			DESCRIPTION
				"Description."
			::= { hwIPSecPkiEntityEntry 5 }
		
--  1.3.6.1.4.1.2011.5.25.224.1.12.1.6
		-- 1.3.6.1.4.1.2011.5.25.224.1.13.1.6
		hwIPSecPkiEntityEmailEnable OBJECT-TYPE
			SYNTAX EnabledStatus
			MAX-ACCESS read-write
			STATUS current
			DESCRIPTION
				"Description."
			DEFVAL { disabled }
			::= { hwIPSecPkiEntityEntry 6 }
		
--  1.3.6.1.4.1.2011.5.25.224.1.12.1.7
		-- 1.3.6.1.4.1.2011.5.25.224.1.13.1.7
		hwIPSecPkiEntityEmail OBJECT-TYPE
			SYNTAX OCTET STRING (SIZE (0..31))
			MAX-ACCESS read-write
			STATUS current
			DESCRIPTION
				"Description."
			::= { hwIPSecPkiEntityEntry 7 }
		
--  1.3.6.1.4.1.2011.5.25.224.1.12.1.8
		-- 1.3.6.1.4.1.2011.5.25.224.1.13.1.8
		hwIPSecPkiEntityFqdnEnable OBJECT-TYPE
			SYNTAX EnabledStatus
			MAX-ACCESS read-write
			STATUS current
			DESCRIPTION
				"Description."
			DEFVAL { disabled }
			::= { hwIPSecPkiEntityEntry 8 }
		
--  1.3.6.1.4.1.2011.5.25.224.1.12.1.9
		-- 1.3.6.1.4.1.2011.5.25.224.1.13.1.9
		hwIPSecPkiEntityFqdn OBJECT-TYPE
			SYNTAX OCTET STRING (SIZE (0..31))
			MAX-ACCESS read-write
			STATUS current
			DESCRIPTION
				"Description."
			::= { hwIPSecPkiEntityEntry 9 }
		
--  1.3.6.1.4.1.2011.5.25.224.1.12.1.10
		-- 1.3.6.1.4.1.2011.5.25.224.1.13.1.10
		hwIPSecPkiEntityIpAddrEnable OBJECT-TYPE
			SYNTAX EnabledStatus
			MAX-ACCESS read-write
			STATUS current
			DESCRIPTION
				"Description."
			DEFVAL { disabled }
			::= { hwIPSecPkiEntityEntry 10 }
		
--  1.3.6.1.4.1.2011.5.25.224.1.12.1.11
		-- 1.3.6.1.4.1.2011.5.25.224.1.13.1.11
		hwIPSecPkiEntityIpAddr OBJECT-TYPE
			SYNTAX IpAddress
			MAX-ACCESS read-write
			STATUS current
			DESCRIPTION
				"Description."
			::= { hwIPSecPkiEntityEntry 11 }
		
--  1.3.6.1.4.1.2011.5.25.224.1.12.1.12
		-- 1.3.6.1.4.1.2011.5.25.224.1.13.1.12
		hwIPSecPkiEntityLocalityEnable OBJECT-TYPE
			SYNTAX EnabledStatus
			MAX-ACCESS read-write
			STATUS current
			DESCRIPTION
				"Description."
			DEFVAL { disabled }
			::= { hwIPSecPkiEntityEntry 12 }
		
--  1.3.6.1.4.1.2011.5.25.224.1.12.1.13
		-- 1.3.6.1.4.1.2011.5.25.224.1.13.1.13
		hwIPSecPkiEntityLocality OBJECT-TYPE
			SYNTAX OCTET STRING (SIZE (0..31))
			MAX-ACCESS read-write
			STATUS current
			DESCRIPTION
				"Description."
			::= { hwIPSecPkiEntityEntry 13 }
		
--  1.3.6.1.4.1.2011.5.25.224.1.12.1.14
		-- 1.3.6.1.4.1.2011.5.25.224.1.13.1.14
		hwIPSecPkiEntityOrgEnable OBJECT-TYPE
			SYNTAX EnabledStatus
			MAX-ACCESS read-write
			STATUS current
			DESCRIPTION
				"Description."
			DEFVAL { disabled }
			::= { hwIPSecPkiEntityEntry 14 }
		
--  1.3.6.1.4.1.2011.5.25.224.1.12.1.15
		-- 1.3.6.1.4.1.2011.5.25.224.1.13.1.15
		hwIPSecPkiEntityOrg OBJECT-TYPE
			SYNTAX OCTET STRING (SIZE (0..31))
			MAX-ACCESS read-write
			STATUS current
			DESCRIPTION
				"Description."
			::= { hwIPSecPkiEntityEntry 15 }
		
--  1.3.6.1.4.1.2011.5.25.224.1.12.1.16
		-- 1.3.6.1.4.1.2011.5.25.224.1.13.1.16
		hwIPSecPkiEntityOrgUnitEnable OBJECT-TYPE
			SYNTAX EnabledStatus
			MAX-ACCESS read-write
			STATUS current
			DESCRIPTION
				"Description."
			DEFVAL { disabled }
			::= { hwIPSecPkiEntityEntry 16 }
		
--  1.3.6.1.4.1.2011.5.25.224.1.12.1.17
		-- 1.3.6.1.4.1.2011.5.25.224.1.13.1.17
		hwIPSecPkiEntityOrgUnit OBJECT-TYPE
			SYNTAX OCTET STRING (SIZE (0..31))
			MAX-ACCESS read-write
			STATUS current
			DESCRIPTION
				"Description."
			::= { hwIPSecPkiEntityEntry 17 }
		
--  1.3.6.1.4.1.2011.5.25.224.1.12.1.18
		-- 1.3.6.1.4.1.2011.5.25.224.1.13.1.18
		hwIPSecPkiEntityStateEnable OBJECT-TYPE
			SYNTAX EnabledStatus
			MAX-ACCESS read-write
			STATUS current
			DESCRIPTION
				"Description."
			DEFVAL { disabled }
			::= { hwIPSecPkiEntityEntry 18 }
		
--  1.3.6.1.4.1.2011.5.25.224.1.12.1.19
		-- 1.3.6.1.4.1.2011.5.25.224.1.13.1.19
		hwIPSecPkiEntityState OBJECT-TYPE
			SYNTAX OCTET STRING (SIZE (0..31))
			MAX-ACCESS read-write
			STATUS current
			DESCRIPTION
				"Description."
			::= { hwIPSecPkiEntityEntry 19 }
		
--  1.3.6.1.4.1.2011.5.25.224.1.12.1.20
		-- 1.3.6.1.4.1.2011.5.25.224.1.13.1.20
		hwIPSecPkiEntityRowStatus OBJECT-TYPE
			SYNTAX RowStatus
			MAX-ACCESS read-create
			STATUS current
			DESCRIPTION
				"Description."
			DEFVAL { active }
			::= { hwIPSecPkiEntityEntry 20 }
		
--  1.3.6.1.4.1.2011.5.25.224.1.13
		-- 1.3.6.1.4.1.2011.5.25.224.1.14
		hwIPSecPkiDomainTable OBJECT-TYPE
			SYNTAX SEQUENCE OF HwIPSecPkiDomainEntry
			MAX-ACCESS not-accessible
			STATUS current
			DESCRIPTION
				"Description."
			::= { hwIPSecObjects 14 }
		
--  1.3.6.1.4.1.2011.5.25.224.1.13.1
		-- 1.3.6.1.4.1.2011.5.25.224.1.14.1
		hwIPSecPkiDomainEntry OBJECT-TYPE
			SYNTAX HwIPSecPkiDomainEntry
			MAX-ACCESS not-accessible
			STATUS current
			DESCRIPTION
				"Description."
			INDEX { hwIPSecPkiDomainName }
			::= { hwIPSecPkiDomainTable 1 }
		
		HwIPSecPkiDomainEntry ::=
			SEQUENCE { 
				hwIPSecPkiDomainName
					OCTET STRING,
				hwIPSecPkiDomainCertReqEntityEnable
					EnabledStatus,
				hwIPSecPkiDomainCertReqEntity
					OCTET STRING,
				hwIPSecPkiDomainCrlAutoUpdateEnable
					EnabledStatus,
				hwIPSecPkiDomainCrlMethod
					INTEGER,
				hwIPSecPkiDomainCrlUrl
					OCTET STRING,
				hwIPSecPkiDomainCrlLdapAttr
					OCTET STRING,
				hwIPSecPkiDomainCrlLdapDn
					OCTET STRING,
				hwIPSecPkiDomainCrlUpdatePeriod
					Integer32,
				hwIPSecPkiDomainLSAuthenName
					OCTET STRING,
				hwIPSecPkiDomainLSAuthenPWD
					OCTET STRING,
				hwIPSecPkiDomainLSIp
					IpAddress,
				hwIPSecPkiDomainLSPort
					Integer32,
				hwIPSecPkiDomainLSSource
					IpAddress,
				hwIPSecPkiDomainLSVersion
					Integer32,
				hwIPSecPkiDomainUndoLdapServer
					EnabledStatus,
				hwIPSecPkiDomainUndoCrlLdapDnAll
					EnabledStatus,
				hwIPSecPkiDomainUndoCrlLdapDn
					OCTET STRING,
				hwIPSecPkiDomainUndoCrlUrlAll
					EnabledStatus,
				hwIPSecPkiDomainUndoCrlUrl
					OCTET STRING,
				hwIPSecPkiDomainRowStatus
					RowStatus
			 }

--  1.3.6.1.4.1.2011.5.25.224.1.13.1.1
		-- 1.3.6.1.4.1.2011.5.25.224.1.14.1.1
		hwIPSecPkiDomainName OBJECT-TYPE
			SYNTAX OCTET STRING (SIZE (0..31))
			MAX-ACCESS read-only
			STATUS current
			DESCRIPTION
				"Description."
			::= { hwIPSecPkiDomainEntry 1 }
		
--  1.3.6.1.4.1.2011.5.25.224.1.13.1.2
		-- 1.3.6.1.4.1.2011.5.25.224.1.14.1.2
		hwIPSecPkiDomainCertReqEntityEnable OBJECT-TYPE
			SYNTAX EnabledStatus
			MAX-ACCESS read-write
			STATUS current
			DESCRIPTION
				"Description."
			DEFVAL { disabled }
			::= { hwIPSecPkiDomainEntry 2 }
		
--  1.3.6.1.4.1.2011.5.25.224.1.13.1.3
		-- 1.3.6.1.4.1.2011.5.25.224.1.14.1.3
		hwIPSecPkiDomainCertReqEntity OBJECT-TYPE
			SYNTAX OCTET STRING (SIZE (0..31))
			MAX-ACCESS read-write
			STATUS current
			DESCRIPTION
				"Description."
			::= { hwIPSecPkiDomainEntry 3 }
		
--  1.3.6.1.4.1.2011.5.25.224.1.13.1.4
		-- 1.3.6.1.4.1.2011.5.25.224.1.14.1.4
		hwIPSecPkiDomainCrlAutoUpdateEnable OBJECT-TYPE
			SYNTAX EnabledStatus
			MAX-ACCESS read-write
			STATUS current
			DESCRIPTION
				"Description."
			DEFVAL { disabled }
			::= { hwIPSecPkiDomainEntry 4 }
		
--  1.3.6.1.4.1.2011.5.25.224.1.13.1.5
		-- 1.3.6.1.4.1.2011.5.25.224.1.14.1.5
		hwIPSecPkiDomainCrlMethod OBJECT-TYPE
			SYNTAX INTEGER
				{
				ldap(1),
				http(2)
				}
			MAX-ACCESS read-write
			STATUS current
			DESCRIPTION
				"Description."
			DEFVAL { http }
			::= { hwIPSecPkiDomainEntry 5 }
		
--  1.3.6.1.4.1.2011.5.25.224.1.13.1.6
		-- 1.3.6.1.4.1.2011.5.25.224.1.14.1.6
		hwIPSecPkiDomainCrlUrl OBJECT-TYPE
			SYNTAX OCTET STRING (SIZE (0..1284))
			MAX-ACCESS read-write
			STATUS current
			DESCRIPTION
				"Description."
			::= { hwIPSecPkiDomainEntry 6 }
		
--  1.3.6.1.4.1.2011.5.25.224.1.13.1.7
		-- 1.3.6.1.4.1.2011.5.25.224.1.14.1.7
		hwIPSecPkiDomainCrlLdapAttr OBJECT-TYPE
			SYNTAX OCTET STRING (SIZE (0..644))
			MAX-ACCESS read-write
			STATUS current
			DESCRIPTION
				"Description."
			::= { hwIPSecPkiDomainEntry 7 }
		
--  1.3.6.1.4.1.2011.5.25.224.1.13.1.8
		-- 1.3.6.1.4.1.2011.5.25.224.1.14.1.8
		hwIPSecPkiDomainCrlLdapDn OBJECT-TYPE
			SYNTAX OCTET STRING (SIZE (0..1284))
			MAX-ACCESS read-write
			STATUS current
			DESCRIPTION
				"Description."
			::= { hwIPSecPkiDomainEntry 8 }
		
--  1.3.6.1.4.1.2011.5.25.224.1.13.1.9
		-- 1.3.6.1.4.1.2011.5.25.224.1.14.1.9
		hwIPSecPkiDomainCrlUpdatePeriod OBJECT-TYPE
			SYNTAX Integer32 (1..720)
			MAX-ACCESS read-write
			STATUS current
			DESCRIPTION
				"Description."
			DEFVAL { 8 }
			::= { hwIPSecPkiDomainEntry 9 }
		
--  1.3.6.1.4.1.2011.5.25.224.1.13.1.10
		-- 1.3.6.1.4.1.2011.5.25.224.1.14.1.10
		hwIPSecPkiDomainLSAuthenName OBJECT-TYPE
			SYNTAX OCTET STRING (SIZE (0..31))
			MAX-ACCESS read-write
			STATUS current
			DESCRIPTION
				"Description."
			::= { hwIPSecPkiDomainEntry 10 }
		
--  1.3.6.1.4.1.2011.5.25.224.1.13.1.11
		-- 1.3.6.1.4.1.2011.5.25.224.1.14.1.11
		hwIPSecPkiDomainLSAuthenPWD OBJECT-TYPE
			SYNTAX OCTET STRING (SIZE (0..31))
			MAX-ACCESS read-write
			STATUS current
			DESCRIPTION
				"Description."
			::= { hwIPSecPkiDomainEntry 11 }
		
--  1.3.6.1.4.1.2011.5.25.224.1.13.1.12
		-- 1.3.6.1.4.1.2011.5.25.224.1.14.1.12
		hwIPSecPkiDomainLSIp OBJECT-TYPE
			SYNTAX IpAddress
			MAX-ACCESS read-write
			STATUS current
			DESCRIPTION
				"Description."
			::= { hwIPSecPkiDomainEntry 12 }
		
--  1.3.6.1.4.1.2011.5.25.224.1.13.1.13
		-- 1.3.6.1.4.1.2011.5.25.224.1.14.1.13
		hwIPSecPkiDomainLSPort OBJECT-TYPE
			SYNTAX Integer32 (1..65535)
			MAX-ACCESS read-write
			STATUS current
			DESCRIPTION
				"Description."
			DEFVAL { 389 }
			::= { hwIPSecPkiDomainEntry 13 }
		
--  1.3.6.1.4.1.2011.5.25.224.1.13.1.14
		-- 1.3.6.1.4.1.2011.5.25.224.1.14.1.14
		hwIPSecPkiDomainLSSource OBJECT-TYPE
			SYNTAX IpAddress
			MAX-ACCESS read-write
			STATUS current
			DESCRIPTION
				"Description."
			::= { hwIPSecPkiDomainEntry 14 }
		
--  1.3.6.1.4.1.2011.5.25.224.1.13.1.14
		-- 1.3.6.1.4.1.2011.5.25.224.1.14.1.15
		hwIPSecPkiDomainLSVersion OBJECT-TYPE
			SYNTAX Integer32 (2..3)
			MAX-ACCESS read-write
			STATUS current
			DESCRIPTION
				"Description."
			DEFVAL { 3 }
			::= { hwIPSecPkiDomainEntry 15 }
		
--  1.3.6.1.4.1.2011.5.25.224.1.13.1.14
		-- 1.3.6.1.4.1.2011.5.25.224.1.14.1.16
		hwIPSecPkiDomainUndoLdapServer OBJECT-TYPE
			SYNTAX EnabledStatus
			MAX-ACCESS read-write
			STATUS current
			DESCRIPTION
				"Description."
			DEFVAL { disable }
			::= { hwIPSecPkiDomainEntry 16 }
		
--  1.3.6.1.4.1.2011.5.25.224.1.13.1.7
		-- 1.3.6.1.4.1.2011.5.25.224.1.14.1.17
		hwIPSecPkiDomainUndoCrlLdapDnAll OBJECT-TYPE
			SYNTAX EnabledStatus
			MAX-ACCESS read-write
			STATUS current
			DESCRIPTION
				"Description."
			DEFVAL { disable }
			::= { hwIPSecPkiDomainEntry 17 }
		
--  1.3.6.1.4.1.2011.5.25.224.1.13.1.7
		-- 1.3.6.1.4.1.2011.5.25.224.1.14.1.18
		hwIPSecPkiDomainUndoCrlLdapDn OBJECT-TYPE
			SYNTAX OCTET STRING (SIZE (0..127))
			MAX-ACCESS read-write
			STATUS current
			DESCRIPTION
				"Description."
			DEFVAL { ''b }
			::= { hwIPSecPkiDomainEntry 18 }
		
--  1.3.6.1.4.1.2011.5.25.224.1.13.1.7
		-- 1.3.6.1.4.1.2011.5.25.224.1.14.1.19
		hwIPSecPkiDomainUndoCrlUrlAll OBJECT-TYPE
			SYNTAX EnabledStatus
			MAX-ACCESS read-write
			STATUS current
			DESCRIPTION
				"Description."
			DEFVAL { disable }
			::= { hwIPSecPkiDomainEntry 19 }
		
--  1.3.6.1.4.1.2011.5.25.224.1.13.1.7
		-- 1.3.6.1.4.1.2011.5.25.224.1.14.1.20
		hwIPSecPkiDomainUndoCrlUrl OBJECT-TYPE
			SYNTAX OCTET STRING (SIZE (0..127))
			MAX-ACCESS read-write
			STATUS current
			DESCRIPTION
				"Description."
			DEFVAL { ''b }
			::= { hwIPSecPkiDomainEntry 20 }
		
--  1.3.6.1.4.1.2011.5.25.224.1.13.1.15
		-- 1.3.6.1.4.1.2011.5.25.224.1.14.1.21
		hwIPSecPkiDomainRowStatus OBJECT-TYPE
			SYNTAX RowStatus
			MAX-ACCESS read-create
			STATUS current
			DESCRIPTION
				"Description."
			DEFVAL { active }
			::= { hwIPSecPkiDomainEntry 21 }
		
--  1.3.6.1.4.1.2011.5.25.224.1.14
		-- 1.3.6.1.4.1.2011.5.25.224.1.15
		hwIPSecPkiCerAttrGrpTable OBJECT-TYPE
			SYNTAX SEQUENCE OF HwIPSecPkiCerAttrGrpEntry
			MAX-ACCESS not-accessible
			STATUS current
			DESCRIPTION
				"Description."
			::= { hwIPSecObjects 15 }
		
--  1.3.6.1.4.1.2011.5.25.224.1.14.1
		-- 1.3.6.1.4.1.2011.5.25.224.1.15.1
		hwIPSecPkiCerAttrGrpEntry OBJECT-TYPE
			SYNTAX HwIPSecPkiCerAttrGrpEntry
			MAX-ACCESS not-accessible
			STATUS current
			DESCRIPTION
				"Description."
			INDEX { hwIPSecPkiCerAttrGrpName, hwIPSecPkiCerAttrGrpPolicyId }
			::= { hwIPSecPkiCerAttrGrpTable 1 }
		
		HwIPSecPkiCerAttrGrpEntry ::=
			SEQUENCE { 
				hwIPSecPkiCerAttrGrpName
					OCTET STRING,
				hwIPSecPkiCerAttrGrpPolicyId
					Integer32,
				hwIPSecPkiCerAttrGrpMode
					INTEGER,
				hwIPSecPkiCerAttrGrpOperate
					INTEGER,
				hwIPSecPkiCerAttrGrpValue
					OCTET STRING,
				hwIPSecPkiCerAttrGrpIp
					IpAddress,
				hwIPSecPkiCerAttrGrpRowStatus
					RowStatus
			 }

--  1.3.6.1.4.1.2011.5.25.224.1.14.1.1
		-- 1.3.6.1.4.1.2011.5.25.224.1.15.1.1
		hwIPSecPkiCerAttrGrpName OBJECT-TYPE
			SYNTAX OCTET STRING (SIZE (0..31))
			MAX-ACCESS read-only
			STATUS current
			DESCRIPTION
				"Description."
			::= { hwIPSecPkiCerAttrGrpEntry 1 }
		
--  1.3.6.1.4.1.2011.5.25.224.1.14.1.2
		-- 1.3.6.1.4.1.2011.5.25.224.1.15.1.2
		hwIPSecPkiCerAttrGrpPolicyId OBJECT-TYPE
			SYNTAX Integer32 (1..256)
			MAX-ACCESS read-only
			STATUS current
			DESCRIPTION
				"Description."
			::= { hwIPSecPkiCerAttrGrpEntry 2 }
		
--  1.3.6.1.4.1.2011.5.25.224.1.14.1.3
		-- 1.3.6.1.4.1.2011.5.25.224.1.15.1.3
		hwIPSecPkiCerAttrGrpMode OBJECT-TYPE
			SYNTAX INTEGER
				{
				altsubnamefqdn(0),
				altsubnameip(1),
				issnamedn(2),
				subnamedn(3)
				}
			MAX-ACCESS read-write
			STATUS current
			DESCRIPTION
				"Description."
			DEFVAL { altsubnamefqdn }
			::= { hwIPSecPkiCerAttrGrpEntry 3 }
		
--  1.3.6.1.4.1.2011.5.25.224.1.14.1.4
		-- 1.3.6.1.4.1.2011.5.25.224.1.15.1.4
		hwIPSecPkiCerAttrGrpOperate OBJECT-TYPE
			SYNTAX INTEGER
				{
				eqn(0),
				nequ(1),
				ctn(2),
				nctn(3)
				}
			MAX-ACCESS read-write
			STATUS current
			DESCRIPTION
				"Description."
			::= { hwIPSecPkiCerAttrGrpEntry 4 }
		
--  1.3.6.1.4.1.2011.5.25.224.1.14.1.5
		-- 1.3.6.1.4.1.2011.5.25.224.1.15.1.5
		hwIPSecPkiCerAttrGrpValue OBJECT-TYPE
			SYNTAX OCTET STRING (SIZE (0..127))
			MAX-ACCESS read-write
			STATUS current
			DESCRIPTION
				"Description."
			::= { hwIPSecPkiCerAttrGrpEntry 5 }
		
--  1.3.6.1.4.1.2011.5.25.224.1.14.1.6
		-- 1.3.6.1.4.1.2011.5.25.224.1.15.1.6
		hwIPSecPkiCerAttrGrpIp OBJECT-TYPE
			SYNTAX IpAddress
			MAX-ACCESS read-write
			STATUS current
			DESCRIPTION
				"Description."
			::= { hwIPSecPkiCerAttrGrpEntry 6 }
		
--  1.3.6.1.4.1.2011.5.25.224.1.14.1.7
		-- 1.3.6.1.4.1.2011.5.25.224.1.15.1.7
		hwIPSecPkiCerAttrGrpRowStatus OBJECT-TYPE
			SYNTAX RowStatus
			MAX-ACCESS read-create
			STATUS current
			DESCRIPTION
				"Description."
			DEFVAL { active }
			::= { hwIPSecPkiCerAttrGrpEntry 7 }
		
--  1.3.6.1.4.1.2011.5.25.224.1.15
		-- 1.3.6.1.4.1.2011.5.25.224.1.16
		hwIPSecPkiCerAccCtlPolicyTable OBJECT-TYPE
			SYNTAX SEQUENCE OF HwIPSecPkiCerAccCtlPolicyEntry
			MAX-ACCESS not-accessible
			STATUS current
			DESCRIPTION
				"Description."
			::= { hwIPSecObjects 16 }
		
--  1.3.6.1.4.1.2011.5.25.224.1.15.1
		-- 1.3.6.1.4.1.2011.5.25.224.1.16.1
		hwIPSecPkiCerAccCtlPolicyEntry OBJECT-TYPE
			SYNTAX HwIPSecPkiCerAccCtlPolicyEntry
			MAX-ACCESS not-accessible
			STATUS current
			DESCRIPTION
				"Description."
			INDEX { hwIPSecPkiCerAccCtlPolicyName, hwIPSecPkiCerAccCtlPolicyId }
			::= { hwIPSecPkiCerAccCtlPolicyTable 1 }
		
		HwIPSecPkiCerAccCtlPolicyEntry ::=
			SEQUENCE { 
				hwIPSecPkiCerAccCtlPolicyName
					OCTET STRING,
				hwIPSecPkiCerAccCtlPolicyId
					Integer32,
				hwIPSecPkiCerAccCtlPolicyMode
					INTEGER,
				hwIPSecPkiCerAccCtlPolicyAttrGrpName
					OCTET STRING,
				hwIPSecPkiCerAccCtlPolicyRowStatus
					RowStatus
			 }

--  1.3.6.1.4.1.2011.5.25.224.1.15.1.1
		-- 1.3.6.1.4.1.2011.5.25.224.1.16.1.1
		hwIPSecPkiCerAccCtlPolicyName OBJECT-TYPE
			SYNTAX OCTET STRING (SIZE (0..31))
			MAX-ACCESS read-only
			STATUS current
			DESCRIPTION
				"Description."
			::= { hwIPSecPkiCerAccCtlPolicyEntry 1 }
		
--  1.3.6.1.4.1.2011.5.25.224.1.15.1.2
		-- 1.3.6.1.4.1.2011.5.25.224.1.16.1.2
		hwIPSecPkiCerAccCtlPolicyId OBJECT-TYPE
			SYNTAX Integer32 (1..256)
			MAX-ACCESS read-only
			STATUS current
			DESCRIPTION
				"Description."
			::= { hwIPSecPkiCerAccCtlPolicyEntry 2 }
		
--  1.3.6.1.4.1.2011.5.25.224.1.15.1.3
		-- 1.3.6.1.4.1.2011.5.25.224.1.16.1.3
		hwIPSecPkiCerAccCtlPolicyMode OBJECT-TYPE
			SYNTAX INTEGER
				{
				deny(0),
				permit(1)
				}
			MAX-ACCESS read-write
			STATUS current
			DESCRIPTION
				"Description."
			::= { hwIPSecPkiCerAccCtlPolicyEntry 3 }
		
--  1.3.6.1.4.1.2011.5.25.224.1.15.1.4
		-- 1.3.6.1.4.1.2011.5.25.224.1.16.1.4
		hwIPSecPkiCerAccCtlPolicyAttrGrpName OBJECT-TYPE
			SYNTAX OCTET STRING (SIZE (0..31))
			MAX-ACCESS read-write
			STATUS current
			DESCRIPTION
				"Description."
			::= { hwIPSecPkiCerAccCtlPolicyEntry 4 }
		
--  1.3.6.1.4.1.2011.5.25.224.1.15.1.5
		-- 1.3.6.1.4.1.2011.5.25.224.1.16.1.5
		hwIPSecPkiCerAccCtlPolicyRowStatus OBJECT-TYPE
			SYNTAX RowStatus
			MAX-ACCESS read-create
			STATUS current
			DESCRIPTION
				"Description."
			DEFVAL { active }
			::= { hwIPSecPkiCerAccCtlPolicyEntry 5 }
		
--   1.3.6.1.4.1.2011.5.25.224.1.7
-- 1.3.6.1.4.1.2011.5.25.224.1.7
		-- 1.3.6.1.4.1.2011.5.25.224.1.17
		hwIPSecEnableSlotTable OBJECT-TYPE
			SYNTAX SEQUENCE OF HwIPSecEnableSlotEntry
			MAX-ACCESS not-accessible
			STATUS current
			DESCRIPTION
				"Description."
			::= { hwIPSecObjects 17 }
		
--   1.3.6.1.4.1.2011.5.25.224.1.7.1
-- 1.3.6.1.4.1.2011.5.25.224.1.7.1
		-- 1.3.6.1.4.1.2011.5.25.224.1.17.1
		hwIPSecEnableSlotEntry OBJECT-TYPE
			SYNTAX HwIPSecEnableSlotEntry
			MAX-ACCESS not-accessible
			STATUS current
			DESCRIPTION
				"Description."
			INDEX { hwIPSecSlotIndex, hwIPSecSlotID }
			::= { hwIPSecEnableSlotTable 1 }
		
		HwIPSecEnableSlotEntry ::=
			SEQUENCE { 
				hwIPSecSlotIndex
					INTEGER,
				hwIPSecSlotID
					Integer32,
				hwIPSecEnable
					EnabledStatus,
				hwIPSecEnableRowStatus
					RowStatus
			 }

--   1.3.6.1.4.1.2011.5.25.224.1.7.1.1
-- 1.3.6.1.4.1.2011.5.25.224.1.7.1.1
		-- 1.3.6.1.4.1.2011.5.25.224.1.17.1.1
		hwIPSecSlotIndex OBJECT-TYPE
			SYNTAX INTEGER { index(1) }
			MAX-ACCESS read-only
			STATUS current
			DESCRIPTION
				"Description."
			::= { hwIPSecEnableSlotEntry 1 }
		
--   1.3.6.1.4.1.2011.5.25.224.1.7.1.2
-- 1.3.6.1.4.1.2011.5.25.224.1.7.1.2
		-- 1.3.6.1.4.1.2011.5.25.224.1.17.1.2
		hwIPSecSlotID OBJECT-TYPE
			SYNTAX Integer32 (1..128)
			MAX-ACCESS read-only
			STATUS current
			DESCRIPTION
				"Description."
			::= { hwIPSecEnableSlotEntry 2 }
		
--   1.3.6.1.4.1.2011.5.25.224.1.7.1.4
-- 1.3.6.1.4.1.2011.5.25.224.1.7.1.4
		-- 1.3.6.1.4.1.2011.5.25.224.1.17.1.3
		hwIPSecEnable OBJECT-TYPE
			SYNTAX EnabledStatus
			MAX-ACCESS read-write
			STATUS current
			DESCRIPTION
				"Description."
			DEFVAL { disable }
			::= { hwIPSecEnableSlotEntry 3 }
		
--  1.3.6.1.4.1.2011.5.25.224.1.15.1.5
		-- 1.3.6.1.4.1.2011.5.25.224.1.17.1.4
		hwIPSecEnableRowStatus OBJECT-TYPE
			SYNTAX RowStatus
			MAX-ACCESS read-create
			STATUS current
			DESCRIPTION
				"Description."
			DEFVAL { active }
			::= { hwIPSecEnableSlotEntry 4 }
		
		-- 1.3.6.1.4.1.2011.5.25.224.1.18
		hwIPSecInstanceTable OBJECT-TYPE
			SYNTAX SEQUENCE OF HwIPSecInstanceEntry
			MAX-ACCESS not-accessible
			STATUS current
			DESCRIPTION
				"Description."
			::= { hwIPSecObjects 18 }
		
		-- 1.3.6.1.4.1.2011.5.25.224.1.18.1
		hwIPSecInstanceEntry OBJECT-TYPE
			SYNTAX HwIPSecInstanceEntry
			MAX-ACCESS not-accessible
			STATUS current
			DESCRIPTION
				"Description."
			INDEX { hwIPSecInstanceID }
			::= { hwIPSecInstanceTable 1 }
		
		HwIPSecInstanceEntry ::=
			SEQUENCE { 
				hwIPSecInstanceID
					Integer32,
				hwIPSecInstanceEnable
					EnabledStatus,
				hwIPSecInstanceRowStatus
					RowStatus
			 }

		-- 1.3.6.1.4.1.2011.5.25.224.1.18.1.1
		hwIPSecInstanceID OBJECT-TYPE
			SYNTAX Integer32 (1..8)
			MAX-ACCESS read-only
			STATUS current
			DESCRIPTION
				"Description."
			::= { hwIPSecInstanceEntry 1 }
		
		-- 1.3.6.1.4.1.2011.5.25.224.1.18.1.2
		hwIPSecInstanceEnable OBJECT-TYPE
			SYNTAX EnabledStatus
			MAX-ACCESS read-write
			STATUS current
			DESCRIPTION
				"Description."
			DEFVAL { disable }
			::= { hwIPSecInstanceEntry 2 }
		
		-- 1.3.6.1.4.1.2011.5.25.224.1.18.1.3
		hwIPSecInstanceRowStatus OBJECT-TYPE
			SYNTAX RowStatus
			UNITS "active"
			MAX-ACCESS read-create
			STATUS current
			DESCRIPTION
				"Description."
			::= { hwIPSecInstanceEntry 3 }
		
--  1.3.6.1.4.1.2011.5.25.224.4.1
		-- 1.3.6.1.4.1.2011.5.25.224.1.19
		hwIPSecStatusObjects OBJECT IDENTIFIER ::= { hwIPSecObjects 19 }
		
--   1.3.6.1.4.1.2011.5.25.224.3.1.1
-- hwIPSecTunnelStatus OBJECT-TYPE
-- SYNTAX Integer32(1..2)
-- MAX-ACCESS accessible-for-notify
-- STATUS current
-- DESCRIPTION
-- "The object indicates the IPSec tunnel status."
-- ::= { hwIPSecStatusObjects 1 }    
-- 1.3.6.1.4.1.2011.5.25.224.3.1.1
-- 1.3.6.1.4.1.2011.5.25.224.4.1.1
		-- 1.3.6.1.4.1.2011.5.25.224.1.19.1
		hwIPSecPolicyName OBJECT-TYPE
			SYNTAX OCTET STRING
			MAX-ACCESS accessible-for-notify
			STATUS current
			DESCRIPTION
				"The object indicates the IPSec Policy name."
			::= { hwIPSecStatusObjects 1 }
		
--   1.3.6.1.4.1.2011.5.25.224.3.1.2
-- 1.3.6.1.4.1.2011.5.25.224.4.1.2
		-- 1.3.6.1.4.1.2011.5.25.224.1.19.2
		hwIPSecPolicySeq OBJECT-TYPE
			SYNTAX Integer32 (1..10000)
			MAX-ACCESS accessible-for-notify
			STATUS current
			DESCRIPTION
				"The object indicates the IPSec Policy sequence number."
			::= { hwIPSecStatusObjects 2 }
		
--   1.3.6.1.4.1.2011.5.25.224.3.1.3
-- 1.3.6.1.4.1.2011.5.25.224.4.1.3
		-- 1.3.6.1.4.1.2011.5.25.224.1.19.3
		hwIPSecInterface OBJECT-TYPE
			SYNTAX OCTET STRING
			MAX-ACCESS accessible-for-notify
			STATUS current
			DESCRIPTION
				"The object indicates the interface that be binded ipsec policy."
			::= { hwIPSecStatusObjects 3 }
		
--   1.3.6.1.4.1.2011.5.25.224.3.1.4
-- 1.3.6.1.4.1.2011.5.25.224.4.1.4
		-- 1.3.6.1.4.1.2011.5.25.224.1.19.4
		hwIPSecLocalIp OBJECT-TYPE
			SYNTAX OCTET STRING
			MAX-ACCESS accessible-for-notify
			STATUS current
			DESCRIPTION
				"The object indicates the IPSec tunnel local ip address."
			::= { hwIPSecStatusObjects 4 }
		
--   1.3.6.1.4.1.2011.5.25.224.3.1.5
-- 1.3.6.1.4.1.2011.5.25.224.4.1.5
		-- 1.3.6.1.4.1.2011.5.25.224.1.19.5
		hwIPSecRemoteIp OBJECT-TYPE
			SYNTAX OCTET STRING
			MAX-ACCESS accessible-for-notify
			STATUS current
			DESCRIPTION
				"The object indicates the IPSec tunnel remote ip address."
			::= { hwIPSecStatusObjects 5 }
		
--   1.3.6.1.4.1.2011.5.25.224.3.1.6
-- 1.3.6.1.4.1.2011.5.25.224.4.1.6
		-- 1.3.6.1.4.1.2011.5.25.224.1.19.6
		hwIPSecRemotePort OBJECT-TYPE
			SYNTAX Integer32 (1..10000)
			MAX-ACCESS accessible-for-notify
			STATUS current
			DESCRIPTION
				"The object indicates the IPSec tunnel remote port."
			::= { hwIPSecStatusObjects 6 }
		
--   1.3.6.1.4.1.2011.5.25.224.3.1.7
-- 1.3.6.1.4.1.2011.5.25.224.4.1.7
		-- 1.3.6.1.4.1.2011.5.25.224.1.19.7
		hwIPSecPkiGetCertUrl OBJECT-TYPE
			SYNTAX OCTET STRING (SIZE (0..127))
			MAX-ACCESS accessible-for-notify
			STATUS current
			DESCRIPTION
				"The object indicates the url to get pki cert."
			::= { hwIPSecStatusObjects 7 }
		
--   1.3.6.1.4.1.2011.5.25.224.3.1.8
-- 1.3.6.1.4.1.2011.5.25.224.4.1.8
		-- 1.3.6.1.4.1.2011.5.25.224.1.19.8
		hwIPSecPkiGetCertIp OBJECT-TYPE
			SYNTAX IpAddress
			MAX-ACCESS accessible-for-notify
			STATUS current
			DESCRIPTION
				"The object indicates the ip to get pki cert."
			::= { hwIPSecStatusObjects 8 }
		
--   1.3.6.1.4.1.2011.5.25.224.3.1.9
-- 1.3.6.1.4.1.2011.5.25.224.4.1.9
		-- 1.3.6.1.4.1.2011.5.25.224.1.19.9
		hwIPSecPkiGetCertPort OBJECT-TYPE
			SYNTAX Integer32 (1..65535)
			MAX-ACCESS accessible-for-notify
			STATUS current
			DESCRIPTION
				"The object indicates the port to get pki cert."
			DEFVAL { 389 }
			::= { hwIPSecStatusObjects 9 }
		
--   1.3.6.1.4.1.2011.5.25.224.3.1.9
-- 1.3.6.1.4.1.2011.5.25.224.4.1.9
		-- 1.3.6.1.4.1.2011.5.25.224.1.19.10
		hwIPSecPkiGetCertLdapVersion OBJECT-TYPE
			SYNTAX Integer32 (1..65535)
			MAX-ACCESS accessible-for-notify
			STATUS current
			DESCRIPTION
				"The object indicates the ldap version to get pki cert."
			::= { hwIPSecStatusObjects 10 }
		
--   1.3.6.1.4.1.2011.5.25.224.3.1.10
-- 1.3.6.1.4.1.2011.5.25.224.4.1.10
		-- 1.3.6.1.4.1.2011.5.25.224.1.19.11
		hwIPSecPkiCertAttr OBJECT-TYPE
			SYNTAX OCTET STRING (SIZE (0..63))
			MAX-ACCESS accessible-for-notify
			STATUS current
			DESCRIPTION
				"The object indicates the attribute to get pki cert."
			::= { hwIPSecStatusObjects 11 }
		
--   1.3.6.1.4.1.2011.5.25.224.3.1.11
-- 1.3.6.1.4.1.2011.5.25.224.4.1.11
		-- 1.3.6.1.4.1.2011.5.25.224.1.19.12
		hwIPSecPkiCertDiffName OBJECT-TYPE
			SYNTAX OCTET STRING (SIZE (0..63))
			MAX-ACCESS accessible-for-notify
			STATUS current
			DESCRIPTION
				"The object indicates the different name to get pki cert."
			::= { hwIPSecStatusObjects 12 }
		
--   1.3.6.1.4.1.2011.5.25.224.3.1.12
-- 1.3.6.1.4.1.2011.5.25.224.4.1.12
		-- 1.3.6.1.4.1.2011.5.25.224.1.19.13
		hwIPSecPkiCAIssuer OBJECT-TYPE
			SYNTAX OCTET STRING (SIZE (0..127))
			MAX-ACCESS accessible-for-notify
			STATUS current
			DESCRIPTION
				"The object indicates the CA issuer."
			::= { hwIPSecStatusObjects 13 }
		
--   1.3.6.1.4.1.2011.5.25.224.3.1.13
-- 1.3.6.1.4.1.2011.5.25.224.4.1.13
		-- 1.3.6.1.4.1.2011.5.25.224.1.19.14
		hwIPSecPkiCASubject OBJECT-TYPE
			SYNTAX OCTET STRING (SIZE (0..127))
			MAX-ACCESS accessible-for-notify
			STATUS current
			DESCRIPTION
				"The object indicates the CA subject."
			::= { hwIPSecStatusObjects 14 }
		
--   1.3.6.1.4.1.2011.5.25.224.3.1.12
-- 1.3.6.1.4.1.2011.5.25.224.4.1.12
		-- 1.3.6.1.4.1.2011.5.25.224.1.19.15
		hwIPSecPkiCrlIssuer OBJECT-TYPE
			SYNTAX OCTET STRING (SIZE (0..127))
			MAX-ACCESS accessible-for-notify
			STATUS current
			DESCRIPTION
				"The object indicates the crl issuer."
			::= { hwIPSecStatusObjects 15 }
		
--   1.3.6.1.4.1.2011.5.25.224.3.1.12
-- 1.3.6.1.4.1.2011.5.25.224.4.1.12
		-- 1.3.6.1.4.1.2011.5.25.224.1.19.16
		hwIPSecPkiStartValidTime OBJECT-TYPE
			SYNTAX TimeTicks
			MAX-ACCESS accessible-for-notify
			STATUS current
			DESCRIPTION
				"The object indicates the start valid time of certificate or crl."
			::= { hwIPSecStatusObjects 16 }
		
--   1.3.6.1.4.1.2011.5.25.224.3.1.12
-- 1.3.6.1.4.1.2011.5.25.224.4.1.12
		-- 1.3.6.1.4.1.2011.5.25.224.1.19.17
		hwIPSecPkiExpiredTime OBJECT-TYPE
			SYNTAX TimeTicks
			MAX-ACCESS accessible-for-notify
			STATUS current
			DESCRIPTION
				"The object indicates the expired time of certificate or crl."
			::= { hwIPSecStatusObjects 17 }

--   1.3.6.1.4.1.2011.5.25.224.1.20
-- 1.3.6.1.4.1.2011.5.25.224.1.20
		-- 1.3.6.1.4.1.2011.5.25.224.1.20
		hwIPSecPerformanceMonitorTable OBJECT-TYPE
			SYNTAX SEQUENCE OF HwIPSecPerformanceMonitorEntry
			MAX-ACCESS not-accessible
			STATUS current
			DESCRIPTION
				"Description."
			::= { hwIPSecObjects 20 }
		
--   1.3.6.1.4.1.2011.5.25.224.1.20.1
-- 1.3.6.1.4.1.2011.5.25.224.1.20.1
		-- 1.3.6.1.4.1.2011.5.25.224.1.20.1
		hwIPSecPerformanceMonitorEntry OBJECT-TYPE
			SYNTAX HwIPSecPerformanceMonitorEntry
			MAX-ACCESS not-accessible
			STATUS current
			DESCRIPTION
				"Description."
			INDEX { hwIPSecMonitorSlotID, hwIPSecMonitorCpuID }
			::= { hwIPSecPerformanceMonitorTable 1 }
		
					
		HwIPSecPerformanceMonitorEntry ::=
			SEQUENCE { 
				hwIPSecMonitorSlotID
					Gauge32,
				hwIPSecMonitorCpuID
					Gauge32,
				hwIPSecMonitorVcpuUsage
					Gauge32,
				hwIPSecMonitorShorterThan64Bytes
					Counter64,
				hwIPSecMonitor64To127Bytes
					Counter64,
				hwIPSecMonitor128To191Bytes
					Counter64,
				hwIPSecMonitor192To255Bytes
					Counter64,
				hwIPSecMonitor256To319Bytes
					Counter64,
				hwIPSecMonitor320To383Bytes
					Counter64,
				hwIPSecMonitor384To447Bytes
					Counter64,
				hwIPSecMonitor448To511Bytes
					Counter64,
				hwIPSecMonitor512To575Bytes
					Counter64,
				hwIPSecMonitor576To639Bytes
					Counter64,
				hwIPSecMonitor640To703Bytes
					Counter64,
				hwIPSecMonitor704To767Bytes
					Counter64,
				hwIPSecMonitor768To831Bytes
					Counter64,
				hwIPSecMonitor832To895Bytes
					Counter64,
				hwIPSecMonitor896To959Bytes
					Counter64,															
				hwIPSecMonitor960To1023Bytes
					Counter64,
				hwIPSecMonitor1024To1500Bytes
					Counter64,					
				hwIPSecMonitorLongerThan1500Bytes
					Counter64,
				hwIPSecMonitorTotalBytes
					Counter64
			 }
	
--   1.3.6.1.4.1.2011.5.25.224.1.20.1.1
-- 1.3.6.1.4.1.2011.5.25.224.1.20.1.1
		-- 1.3.6.1.4.1.2011.5.25.224.1.20.1.1
		hwIPSecMonitorSlotID OBJECT-TYPE
			SYNTAX Gauge32 (1..128)
			MAX-ACCESS read-only
			STATUS current
			DESCRIPTION
				"Description."
			::= { hwIPSecPerformanceMonitorEntry 1 }
		
--   1.3.6.1.4.1.2011.5.25.224.1.20.1.2
-- 1.3.6.1.4.1.2011.5.25.224.1.20.1.2
		-- 1.3.6.1.4.1.2011.5.25.224.1.20.1.2
		hwIPSecMonitorCpuID OBJECT-TYPE
			SYNTAX Gauge32 (0..3)
			MAX-ACCESS read-only
			STATUS current
			DESCRIPTION
				"Description."
			::= { hwIPSecPerformanceMonitorEntry 2 }
					
--   1.3.6.1.4.1.2011.5.25.224.1.20.1.3
-- 1.3.6.1.4.1.2011.5.25.224.1.20.1.3
		-- 1.3.6.1.4.1.2011.5.25.224.1.20.1.3
		hwIPSecMonitorVcpuUsage OBJECT-TYPE
			SYNTAX Gauge32 (0..100)
			MAX-ACCESS read-only
			STATUS current
			DESCRIPTION
				"Description."
			DEFVAL { 0 }
			::= { hwIPSecPerformanceMonitorEntry 3 }

--   1.3.6.1.4.1.2011.5.25.224.1.20.1.4
-- 1.3.6.1.4.1.2011.5.25.224.1.20.1.4
		-- 1.3.6.1.4.1.2011.5.25.224.1.20.1.4
		hwIPSecMonitorShorterThan64Bytes OBJECT-TYPE
			SYNTAX Counter64
			MAX-ACCESS read-only
			STATUS current
			DESCRIPTION
				"Description."
			::= { hwIPSecPerformanceMonitorEntry 4 }

--   1.3.6.1.4.1.2011.5.25.224.1.20.1.5
-- 1.3.6.1.4.1.2011.5.25.224.1.20.1.5
		-- 1.3.6.1.4.1.2011.5.25.224.1.20.1.5
		hwIPSecMonitor64To127Bytes OBJECT-TYPE
			SYNTAX Counter64
			MAX-ACCESS read-only
			STATUS current
			DESCRIPTION
				"Description."
			::= { hwIPSecPerformanceMonitorEntry 5 }

--   1.3.6.1.4.1.2011.5.25.224.1.20.1.6
-- 1.3.6.1.4.1.2011.5.25.224.1.20.1.6
		-- 1.3.6.1.4.1.2011.5.25.224.1.20.1.6
		hwIPSecMonitor128To191Bytes OBJECT-TYPE
			SYNTAX Counter64
			MAX-ACCESS read-only
			STATUS current
			DESCRIPTION
				"Description."
			::= { hwIPSecPerformanceMonitorEntry 6 }
			
--   1.3.6.1.4.1.2011.5.25.224.1.20.1.7
-- 1.3.6.1.4.1.2011.5.25.224.1.20.1.7
		-- 1.3.6.1.4.1.2011.5.25.224.1.20.1.7
		hwIPSecMonitor192To255Bytes OBJECT-TYPE
			SYNTAX Counter64
			MAX-ACCESS read-only
			STATUS current
			DESCRIPTION
				"Description."
			::= { hwIPSecPerformanceMonitorEntry 7 }

--   1.3.6.1.4.1.2011.5.25.224.1.20.1.8
-- 1.3.6.1.4.1.2011.5.25.224.1.20.1.8
		-- 1.3.6.1.4.1.2011.5.25.224.1.20.1.8
		hwIPSecMonitor256To319Bytes OBJECT-TYPE
			SYNTAX Counter64
			MAX-ACCESS read-only
			STATUS current
			DESCRIPTION
				"Description."
			::= { hwIPSecPerformanceMonitorEntry 8 }

--   1.3.6.1.4.1.2011.5.25.224.1.20.1.9
-- 1.3.6.1.4.1.2011.5.25.224.1.20.1.9
		-- 1.3.6.1.4.1.2011.5.25.224.1.20.1.9
		hwIPSecMonitor320To383Bytes OBJECT-TYPE
			SYNTAX Counter64
			MAX-ACCESS read-only
			STATUS current
			DESCRIPTION
				"Description."
			::= { hwIPSecPerformanceMonitorEntry 9 }

--   1.3.6.1.4.1.2011.5.25.224.1.20.1.10
-- 1.3.6.1.4.1.2011.5.25.224.1.20.1.10
		-- 1.3.6.1.4.1.2011.5.25.224.1.20.1.10
		hwIPSecMonitor384To447Bytes OBJECT-TYPE
			SYNTAX Counter64
			MAX-ACCESS read-only
			STATUS current
			DESCRIPTION
				"Description."
			::= { hwIPSecPerformanceMonitorEntry 10 }
			
--   1.3.6.1.4.1.2011.5.25.224.1.20.1.11
-- 1.3.6.1.4.1.2011.5.25.224.1.20.1.11
		-- 1.3.6.1.4.1.2011.5.25.224.1.20.1.11
		hwIPSecMonitor448To511Bytes OBJECT-TYPE
			SYNTAX Counter64
			MAX-ACCESS read-only
			STATUS current
			DESCRIPTION
				"Description."
			::= { hwIPSecPerformanceMonitorEntry 11 }
			
--   1.3.6.1.4.1.2011.5.25.224.1.20.1.12
-- 1.3.6.1.4.1.2011.5.25.224.1.20.1.12
		-- 1.3.6.1.4.1.2011.5.25.224.1.20.1.12
		hwIPSecMonitor512To575Bytes OBJECT-TYPE
			SYNTAX Counter64
			MAX-ACCESS read-only
			STATUS current
			DESCRIPTION
				"Description."
			::= { hwIPSecPerformanceMonitorEntry 12 }
			
--   1.3.6.1.4.1.2011.5.25.224.1.20.1.13
-- 1.3.6.1.4.1.2011.5.25.224.1.20.1.13
		-- 1.3.6.1.4.1.2011.5.25.224.1.20.1.13
		hwIPSecMonitor576To639Bytes OBJECT-TYPE
			SYNTAX Counter64
			MAX-ACCESS read-only
			STATUS current
			DESCRIPTION
				"Description."
			::= { hwIPSecPerformanceMonitorEntry 13 }
			
--   1.3.6.1.4.1.2011.5.25.224.1.20.1.14
-- 1.3.6.1.4.1.2011.5.25.224.1.20.1.14
		-- 1.3.6.1.4.1.2011.5.25.224.1.20.1.14
		hwIPSecMonitor640To703Bytes OBJECT-TYPE
			SYNTAX Counter64
			MAX-ACCESS read-only
			STATUS current
			DESCRIPTION
				"Description."
			::= { hwIPSecPerformanceMonitorEntry 14 }
			
--   1.3.6.1.4.1.2011.5.25.224.1.20.1.15
-- 1.3.6.1.4.1.2011.5.25.224.1.20.1.15
		-- 1.3.6.1.4.1.2011.5.25.224.1.20.1.15
		hwIPSecMonitor704To767Bytes OBJECT-TYPE
			SYNTAX Counter64
			MAX-ACCESS read-only
			STATUS current
			DESCRIPTION
				"Description."
			::= { hwIPSecPerformanceMonitorEntry 15 }
			
--   1.3.6.1.4.1.2011.5.25.224.1.20.1.16
-- 1.3.6.1.4.1.2011.5.25.224.1.20.1.16
		-- 1.3.6.1.4.1.2011.5.25.224.1.20.1.16
		hwIPSecMonitor768To831Bytes OBJECT-TYPE
			SYNTAX Counter64
			MAX-ACCESS read-only
			STATUS current
			DESCRIPTION
				"Description."
			::= { hwIPSecPerformanceMonitorEntry 16 }
			
--   1.3.6.1.4.1.2011.5.25.224.1.20.1.17
-- 1.3.6.1.4.1.2011.5.25.224.1.20.1.17
		-- 1.3.6.1.4.1.2011.5.25.224.1.20.1.17
		hwIPSecMonitor832To895Bytes OBJECT-TYPE
			SYNTAX Counter64
			MAX-ACCESS read-only
			STATUS current
			DESCRIPTION
				"Description."
			::= { hwIPSecPerformanceMonitorEntry 17 }
			
--   1.3.6.1.4.1.2011.5.25.224.1.20.1.18
-- 1.3.6.1.4.1.2011.5.25.224.1.20.1.18
		-- 1.3.6.1.4.1.2011.5.25.224.1.20.1.18
		hwIPSecMonitor896To959Bytes OBJECT-TYPE
			SYNTAX Counter64
			MAX-ACCESS read-only
			STATUS current
			DESCRIPTION
				"Description."
			::= { hwIPSecPerformanceMonitorEntry 18 }
			
--   1.3.6.1.4.1.2011.5.25.224.1.20.1.19
-- 1.3.6.1.4.1.2011.5.25.224.1.20.1.19
		-- 1.3.6.1.4.1.2011.5.25.224.1.20.1.19
		hwIPSecMonitor960To1023Bytes OBJECT-TYPE
			SYNTAX Counter64
			MAX-ACCESS read-only
			STATUS current
			DESCRIPTION
				"Description."
			::= { hwIPSecPerformanceMonitorEntry 19 }
			
--   1.3.6.1.4.1.2011.5.25.224.1.20.1.20
-- 1.3.6.1.4.1.2011.5.25.224.1.20.1.20
		-- 1.3.6.1.4.1.2011.5.25.224.1.20.1.20
		hwIPSecMonitor1024To1500Bytes OBJECT-TYPE
			SYNTAX Counter64
			MAX-ACCESS read-only
			STATUS current
			DESCRIPTION
				"Description."
			::= { hwIPSecPerformanceMonitorEntry 20 }
			
--   1.3.6.1.4.1.2011.5.25.224.1.20.1.21
-- 1.3.6.1.4.1.2011.5.25.224.1.20.1.21
		-- 1.3.6.1.4.1.2011.5.25.224.1.20.1.21
		hwIPSecMonitorLongerThan1500Bytes OBJECT-TYPE
			SYNTAX Counter64
			MAX-ACCESS read-only
			STATUS current
			DESCRIPTION
				"Description."
			::= { hwIPSecPerformanceMonitorEntry 21 }
			
--   1.3.6.1.4.1.2011.5.25.224.1.20.1.22
-- 1.3.6.1.4.1.2011.5.25.224.1.20.1.22
		-- 1.3.6.1.4.1.2011.5.25.224.1.20.1.22
		hwIPSecMonitorTotalBytes OBJECT-TYPE
			SYNTAX Counter64
			MAX-ACCESS read-only
			STATUS current
			DESCRIPTION
				"Description."
			::= { hwIPSecPerformanceMonitorEntry 22 }															


--   1.3.6.1.4.1.2011.5.25.224.1.21
-- 1.3.6.1.4.1.2011.5.25.224.1.21
		-- 1.3.6.1.4.1.2011.5.25.224.1.21
		hwIPSecMulBoardPerformanceMonitorTable OBJECT-TYPE
			SYNTAX SEQUENCE OF HwIPSecMulBoardPerformanceMonitorEntry
			MAX-ACCESS not-accessible
			STATUS current
			DESCRIPTION
				"Description."
			::= { hwIPSecObjects 21 }
		
--   1.3.6.1.4.1.2011.5.25.224.1.21.1
-- 1.3.6.1.4.1.2011.5.25.224.1.21.1
		-- 1.3.6.1.4.1.2011.5.25.224.1.21.1
		hwIPSecMulBoardPerformanceMonitorEntry OBJECT-TYPE
			SYNTAX HwIPSecMulBoardPerformanceMonitorEntry
			MAX-ACCESS not-accessible
			STATUS current
			DESCRIPTION
				"Description."
			INDEX { hwIPSecMulBoardMonitorSlotIDStr, hwIPSecMulBoardMonitorCpuID }
			::= { hwIPSecMulBoardPerformanceMonitorTable 1 }
		
					
		HwIPSecMulBoardPerformanceMonitorEntry ::=
			SEQUENCE {     
			                     hwIPSecMulBoardMonitorSlotIDStr
					OCTET STRING,
				hwIPSecMulBoardMonitorCpuID
					Gauge32,
				hwIPSecMulBoardMonitorVcpuUsage
					Gauge32,
				hwIPSecMulBoardMonitorShorterThan64Bytes
					Counter64,
				hwIPSecMulBoardMonitor64To127Bytes
					Counter64,
				hwIPSecMulBoardMonitor128To191Bytes
					Counter64,
				hwIPSecMulBoardMonitor192To255Bytes
					Counter64,
				hwIPSecMulBoardMonitor256To319Bytes
					Counter64,
				hwIPSecMulBoardMonitor320To383Bytes
					Counter64,
				hwIPSecMulBoardMonitor384To447Bytes
					Counter64,
				hwIPSecMulBoardMonitor448To511Bytes
					Counter64,
				hwIPSecMulBoardMonitor512To575Bytes
					Counter64,
				hwIPSecMulBoardMonitor576To639Bytes
					Counter64,
				hwIPSecMulBoardMonitor640To703Bytes
					Counter64,
				hwIPSecMulBoardMonitor704To767Bytes
					Counter64,
				hwIPSecMulBoardMonitor768To831Bytes
					Counter64,
				hwIPSecMulBoardMonitor832To895Bytes
					Counter64,
				hwIPSecMulBoardMonitor896To959Bytes
					Counter64,															
				hwIPSecMulBoardMonitor960To1023Bytes
					Counter64,
				hwIPSecMulBoardMonitor1024To1500Bytes
					Counter64,					
				hwIPSecMulBoardMonitorLongerThan1500Bytes
					Counter64,
				hwIPSecMulBoardMonitorTotalBytes
					Counter64
			 }

--   1.3.6.1.4.1.2011.5.25.224.1.21.1.1
-- 1.3.6.1.4.1.2011.5.25.224.1.21.1.1
		-- 1.3.6.1.4.1.2011.5.25.224.1.21.1.1
		hwIPSecMulBoardMonitorSlotIDStr OBJECT-TYPE
			SYNTAX OCTET STRING
			MAX-ACCESS read-only
			STATUS current
			DESCRIPTION
				"Description."
			::= { hwIPSecMulBoardPerformanceMonitorEntry 1 }
		
--   1.3.6.1.4.1.2011.5.25.224.1.21.1.2
-- 1.3.6.1.4.1.2011.5.25.224.1.21.1.2
		-- 1.3.6.1.4.1.2011.5.25.224.1.21.1.2
		hwIPSecMulBoardMonitorCpuID OBJECT-TYPE
			SYNTAX Gauge32
			MAX-ACCESS read-only
			STATUS current
			DESCRIPTION
				"Description."
			::= { hwIPSecMulBoardPerformanceMonitorEntry 2 }
					
--   1.3.6.1.4.1.2011.5.25.224.1.21.1.3
-- 1.3.6.1.4.1.2011.5.25.224.1.21.1.3
		-- 1.3.6.1.4.1.2011.5.25.224.1.21.1.3
		hwIPSecMulBoardMonitorVcpuUsage OBJECT-TYPE
			SYNTAX Gauge32
			MAX-ACCESS read-only
			STATUS current
			DESCRIPTION
				"Description."
			DEFVAL { 0 }
			::= { hwIPSecMulBoardPerformanceMonitorEntry 3 }

--   1.3.6.1.4.1.2011.5.25.224.1.21.1.4
-- 1.3.6.1.4.1.2011.5.25.224.1.21.1.4
		-- 1.3.6.1.4.1.2011.5.25.224.1.21.1.4
		hwIPSecMulBoardMonitorShorterThan64Bytes OBJECT-TYPE
			SYNTAX Counter64
			MAX-ACCESS read-only
			STATUS current
			DESCRIPTION
				"Description."
			::= { hwIPSecMulBoardPerformanceMonitorEntry 4 }

--   1.3.6.1.4.1.2011.5.25.224.1.21.1.5
-- 1.3.6.1.4.1.2011.5.25.224.1.21.1.5
		-- 1.3.6.1.4.1.2011.5.25.224.1.21.1.5
		hwIPSecMulBoardMonitor64To127Bytes OBJECT-TYPE
			SYNTAX Counter64
			MAX-ACCESS read-only
			STATUS current
			DESCRIPTION
				"Description."
			::= { hwIPSecMulBoardPerformanceMonitorEntry 5 }

--   1.3.6.1.4.1.2011.5.25.224.1.21.1.6
-- 1.3.6.1.4.1.2011.5.25.224.1.21.1.6
		-- 1.3.6.1.4.1.2011.5.25.224.1.21.1.6
		hwIPSecMulBoardMonitor128To191Bytes OBJECT-TYPE
			SYNTAX Counter64
			MAX-ACCESS read-only
			STATUS current
			DESCRIPTION
				"Description."
			::= { hwIPSecMulBoardPerformanceMonitorEntry 6 }
			
--   1.3.6.1.4.1.2011.5.25.224.1.21.1.7
-- 1.3.6.1.4.1.2011.5.25.224.1.21.1.7
		-- 1.3.6.1.4.1.2011.5.25.224.1.21.1.7
		hwIPSecMulBoardMonitor192To255Bytes OBJECT-TYPE
			SYNTAX Counter64
			MAX-ACCESS read-only
			STATUS current
			DESCRIPTION
				"Description."
			::= { hwIPSecMulBoardPerformanceMonitorEntry 7 }

--   1.3.6.1.4.1.2011.5.25.224.1.21.1.8
-- 1.3.6.1.4.1.2011.5.25.224.1.21.1.8
		-- 1.3.6.1.4.1.2011.5.25.224.1.21.1.8
		hwIPSecMulBoardMonitor256To319Bytes OBJECT-TYPE
			SYNTAX Counter64
			MAX-ACCESS read-only
			STATUS current
			DESCRIPTION
				"Description."
			::= { hwIPSecMulBoardPerformanceMonitorEntry 8 }

--   1.3.6.1.4.1.2011.5.25.224.1.21.1.9
-- 1.3.6.1.4.1.2011.5.25.224.1.21.1.9
		-- 1.3.6.1.4.1.2011.5.25.224.1.21.1.9
		hwIPSecMulBoardMonitor320To383Bytes OBJECT-TYPE
			SYNTAX Counter64
			MAX-ACCESS read-only
			STATUS current
			DESCRIPTION
				"Description."
			::= { hwIPSecMulBoardPerformanceMonitorEntry 9 }

--   1.3.6.1.4.1.2011.5.25.224.1.21.1.10
-- 1.3.6.1.4.1.2011.5.25.224.1.21.1.10
		-- 1.3.6.1.4.1.2011.5.25.224.1.21.1.10
		hwIPSecMulBoardMonitor384To447Bytes OBJECT-TYPE
			SYNTAX Counter64
			MAX-ACCESS read-only
			STATUS current
			DESCRIPTION
				"Description."
			::= { hwIPSecMulBoardPerformanceMonitorEntry 10 }
			
--   1.3.6.1.4.1.2011.5.25.224.1.21.1.11
-- 1.3.6.1.4.1.2011.5.25.224.1.21.1.11
		-- 1.3.6.1.4.1.2011.5.25.224.1.21.1.11
		hwIPSecMulBoardMonitor448To511Bytes OBJECT-TYPE
			SYNTAX Counter64
			MAX-ACCESS read-only
			STATUS current
			DESCRIPTION
				"Description."
			::= { hwIPSecMulBoardPerformanceMonitorEntry 11 }
			
--   1.3.6.1.4.1.2011.5.25.224.1.21.1.12
-- 1.3.6.1.4.1.2011.5.25.224.1.21.1.12
		-- 1.3.6.1.4.1.2011.5.25.224.1.21.1.12
		hwIPSecMulBoardMonitor512To575Bytes OBJECT-TYPE
			SYNTAX Counter64
			MAX-ACCESS read-only
			STATUS current
			DESCRIPTION
				"Description."
			::= { hwIPSecMulBoardPerformanceMonitorEntry 12 }
			
--   1.3.6.1.4.1.2011.5.25.224.1.21.1.13
-- 1.3.6.1.4.1.2011.5.25.224.1.21.1.13
		-- 1.3.6.1.4.1.2011.5.25.224.1.21.1.13
		hwIPSecMulBoardMonitor576To639Bytes OBJECT-TYPE
			SYNTAX Counter64
			MAX-ACCESS read-only
			STATUS current
			DESCRIPTION
				"Description."
			::= { hwIPSecMulBoardPerformanceMonitorEntry 13 }
			
--   1.3.6.1.4.1.2011.5.25.224.1.21.1.14
-- 1.3.6.1.4.1.2011.5.25.224.1.21.1.14
		-- 1.3.6.1.4.1.2011.5.25.224.1.21.1.14
		hwIPSecMulBoardMonitor640To703Bytes OBJECT-TYPE
			SYNTAX Counter64
			MAX-ACCESS read-only
			STATUS current
			DESCRIPTION
				"Description."
			::= { hwIPSecMulBoardPerformanceMonitorEntry 14 }
			
--   1.3.6.1.4.1.2011.5.25.224.1.21.1.15
-- 1.3.6.1.4.1.2011.5.25.224.1.21.1.15
		-- 1.3.6.1.4.1.2011.5.25.224.1.21.1.15
		hwIPSecMulBoardMonitor704To767Bytes OBJECT-TYPE
			SYNTAX Counter64
			MAX-ACCESS read-only
			STATUS current
			DESCRIPTION
				"Description."
			::= { hwIPSecMulBoardPerformanceMonitorEntry 15 }
			
--   1.3.6.1.4.1.2011.5.25.224.1.21.1.16
-- 1.3.6.1.4.1.2011.5.25.224.1.21.1.16
		-- 1.3.6.1.4.1.2011.5.25.224.1.21.1.16
		hwIPSecMulBoardMonitor768To831Bytes OBJECT-TYPE
			SYNTAX Counter64
			MAX-ACCESS read-only
			STATUS current
			DESCRIPTION
				"Description."
			::= { hwIPSecMulBoardPerformanceMonitorEntry 16 }
			
--   1.3.6.1.4.1.2011.5.25.224.1.21.1.17
-- 1.3.6.1.4.1.2011.5.25.224.1.21.1.17
		-- 1.3.6.1.4.1.2011.5.25.224.1.21.1.17
		hwIPSecMulBoardMonitor832To895Bytes OBJECT-TYPE
			SYNTAX Counter64
			MAX-ACCESS read-only
			STATUS current
			DESCRIPTION
				"Description."
			::= { hwIPSecMulBoardPerformanceMonitorEntry 17 }
			
--   1.3.6.1.4.1.2011.5.25.224.1.21.1.18
-- 1.3.6.1.4.1.2011.5.25.224.1.21.1.18
		-- 1.3.6.1.4.1.2011.5.25.224.1.21.1.18
		hwIPSecMulBoardMonitor896To959Bytes OBJECT-TYPE
			SYNTAX Counter64
			MAX-ACCESS read-only
			STATUS current
			DESCRIPTION
				"Description."
			::= { hwIPSecMulBoardPerformanceMonitorEntry 18 }
			
--   1.3.6.1.4.1.2011.5.25.224.1.21.1.19
-- 1.3.6.1.4.1.2011.5.25.224.1.21.1.19
		-- 1.3.6.1.4.1.2011.5.25.224.1.21.1.19
		hwIPSecMulBoardMonitor960To1023Bytes OBJECT-TYPE
			SYNTAX Counter64
			MAX-ACCESS read-only
			STATUS current
			DESCRIPTION
				"Description."
			::= { hwIPSecMulBoardPerformanceMonitorEntry 19 }
			
--   1.3.6.1.4.1.2011.5.25.224.1.21.1.20
-- 1.3.6.1.4.1.2011.5.25.224.1.21.1.20
		-- 1.3.6.1.4.1.2011.5.25.224.1.21.1.20
		hwIPSecMulBoardMonitor1024To1500Bytes OBJECT-TYPE
			SYNTAX Counter64
			MAX-ACCESS read-only
			STATUS current
			DESCRIPTION
				"Description."
			::= { hwIPSecMulBoardPerformanceMonitorEntry 20 }
			
--   1.3.6.1.4.1.2011.5.25.224.1.21.1.21
-- 1.3.6.1.4.1.2011.5.25.224.1.21.1.21
		-- 1.3.6.1.4.1.2011.5.25.224.1.21.1.21
		    hwIPSecMulBoardMonitorLongerThan1500Bytes OBJECT-TYPE
			SYNTAX Counter64
			MAX-ACCESS read-only
			STATUS current
			DESCRIPTION
				"Description."
			::= { hwIPSecMulBoardPerformanceMonitorEntry 21 }
			
--   1.3.6.1.4.1.2011.5.25.224.1.21.1.22
-- 1.3.6.1.4.1.2011.5.25.224.1.21.1.22
		-- 1.3.6.1.4.1.2011.5.25.224.1.21.1.22
		hwIPSecMulBoardMonitorTotalBytes OBJECT-TYPE
			SYNTAX Counter64
			MAX-ACCESS read-only
			STATUS current
			DESCRIPTION
				"Description."
			::= { hwIPSecMulBoardPerformanceMonitorEntry 22 }										
										
				
--   1.3.6.1.4.1.2011.5.25.224.3
-- 1.3.6.1.4.1.2011.5.25.224.4
		-- 1.3.6.1.4.1.2011.5.25.224.2
		hwIPSecNoitfy OBJECT IDENTIFIER ::= { hwIPSecMIB 2 }
		
--  1.3.6.1.4.1.2011.5.25.224.4.2
		-- 1.3.6.1.4.1.2011.5.25.224.2.1
		hwIPSecNotifications OBJECT IDENTIFIER ::= { hwIPSecNoitfy 1 }
		
--   1.3.6.1.4.1.2011.5.25.224.3.2.1        
-- 1.3.6.1.4.1.2011.5.25.224.4.2.1
		-- 1.3.6.1.4.1.2011.5.25.224.2.1.1
		hwIPSecTunnelStateUp NOTIFICATION-TYPE
			OBJECTS { hwIPSecPolicyName, hwIPSecPolicySeq, hwIPSecInterface, hwIPSecLocalIp, hwIPSecRemoteIp, 
				hwIPSecRemotePort }
			STATUS current
			DESCRIPTION 
				"IPSec tunnel statues is up."
			::= { hwIPSecNotifications 1 }
		
--   1.3.6.1.4.1.2011.5.25.224.3.2.2
-- 1.3.6.1.4.1.2011.5.25.224.4.2.2
		-- 1.3.6.1.4.1.2011.5.25.224.2.1.2
		hwIPSecTunnelStateDown NOTIFICATION-TYPE
			OBJECTS { hwIPSecPolicyName, hwIPSecPolicySeq, hwIPSecInterface, hwIPSecLocalIp, hwIPSecRemoteIp, 
				hwIPSecRemotePort }
			STATUS current
			DESCRIPTION 
				"IPSec tunnel statues is dowm."
			::= { hwIPSecNotifications 2 }
		
--   1.3.6.1.4.1.2011.5.25.224.3.2.3
-- 1.3.6.1.4.1.2011.5.25.224.4.2.3
		-- 1.3.6.1.4.1.2011.5.25.224.2.1.3
		hwIPSecPkiHttpGetCrlSuccess NOTIFICATION-TYPE
			OBJECTS { hwIPSecPkiGetCertUrl }
			STATUS current
			DESCRIPTION 
				"IPSec get crl by http success."
			::= { hwIPSecNotifications 3 }
		
--   1.3.6.1.4.1.2011.5.25.224.3.2.4
-- 1.3.6.1.4.1.2011.5.25.224.4.2.4
		-- 1.3.6.1.4.1.2011.5.25.224.2.1.4
		hwIPSecPkiHttpGetCrlFail NOTIFICATION-TYPE
			OBJECTS { hwIPSecPkiGetCertUrl }
			STATUS current
			DESCRIPTION 
				"IPSec get crl by http failed."
			::= { hwIPSecNotifications 4 }
		
--   1.3.6.1.4.1.2011.5.25.224.3.2.5
-- 1.3.6.1.4.1.2011.5.25.224.4.2.5
		-- 1.3.6.1.4.1.2011.5.25.224.2.1.5
		hwIPSecPkiLdapGetCrlSuccess NOTIFICATION-TYPE
			OBJECTS { hwIPSecPkiGetCertIp, hwIPSecPkiGetCertPort, hwIPSecPkiCertAttr, hwIPSecPkiCertDiffName, hwIPSecPkiGetCertLdapVersion 
				 }
			STATUS current
			DESCRIPTION 
				"IPSec get crl by ldap success."
			::= { hwIPSecNotifications 5 }
		
--   1.3.6.1.4.1.2011.5.25.224.3.2.6
-- 1.3.6.1.4.1.2011.5.25.224.4.2.6
		-- 1.3.6.1.4.1.2011.5.25.224.2.1.6
		hwIPSecPkiLdapGetCrlFail NOTIFICATION-TYPE
			OBJECTS { hwIPSecPkiGetCertIp, hwIPSecPkiGetCertPort, hwIPSecPkiCertAttr, hwIPSecPkiCertDiffName, hwIPSecPkiGetCertLdapVersion
				 }
			STATUS current
			DESCRIPTION 
				"IPSec get crl by ldap failed."
			::= { hwIPSecNotifications 6 }
		
--   1.3.6.1.4.1.2011.5.25.224.3.2.7
-- 1.3.6.1.4.1.2011.5.25.224.4.2.7
		-- 1.3.6.1.4.1.2011.5.25.224.2.1.7
		hwIPSecPkiHttpGetCertSuccess NOTIFICATION-TYPE
			OBJECTS { hwIPSecPkiGetCertUrl }
			STATUS current
			DESCRIPTION 
				"IPSec get cert by http success."
			::= { hwIPSecNotifications 7 }
		
--   1.3.6.1.4.1.2011.5.25.224.3.2.8
-- 1.3.6.1.4.1.2011.5.25.224.4.2.8
		-- 1.3.6.1.4.1.2011.5.25.224.2.1.8
		hwIPSecPkiHttpGetCertFail NOTIFICATION-TYPE
			OBJECTS { hwIPSecPkiGetCertUrl }
			STATUS current
			DESCRIPTION 
				"IPSec get cert by http fail"
			::= { hwIPSecNotifications 8 }
		
--   1.3.6.1.4.1.2011.5.25.224.3.2.9
-- 1.3.6.1.4.1.2011.5.25.224.4.2.9
		-- 1.3.6.1.4.1.2011.5.25.224.2.1.9
		hwIPSecPkiLdapGetCertSuccess NOTIFICATION-TYPE
			OBJECTS { hwIPSecPkiGetCertIp, hwIPSecPkiGetCertPort, hwIPSecPkiCertAttr, hwIPSecPkiCertDiffName, hwIPSecPkiGetCertLdapVersion 
				 }
			STATUS current
			DESCRIPTION 
				"IPSec get cert by ldap success."
			::= { hwIPSecNotifications 9 }
		
--   1.3.6.1.4.1.2011.5.25.224.3.2.10
-- 1.3.6.1.4.1.2011.5.25.224.4.2.10
		-- 1.3.6.1.4.1.2011.5.25.224.2.1.10
		hwIPSecPkiLdapGetCertFail NOTIFICATION-TYPE
			OBJECTS { hwIPSecPkiGetCertIp, hwIPSecPkiGetCertPort, hwIPSecPkiCertAttr, hwIPSecPkiCertDiffName, hwIPSecPkiGetCertLdapVersion 
				 }
			STATUS current
			DESCRIPTION 
				"IPSec get cert by ldap fail"
			::= { hwIPSecNotifications 10 }
		
--   1.3.6.1.4.1.2011.5.25.224.3.2.11
-- 1.3.6.1.4.1.2011.5.25.224.4.2.11
		-- 1.3.6.1.4.1.2011.5.25.224.2.1.11
		hwIPSecPkiCACertInValid NOTIFICATION-TYPE
			OBJECTS { hwIPSecPkiStartValidTime, hwIPSecPkiExpiredTime, hwIPSecPkiCAIssuer, hwIPSecPkiCASubject }
			STATUS current
			DESCRIPTION 
				"IPsec pki CA certificate is invalid."
			::= { hwIPSecNotifications 11 }
		
--   1.3.6.1.4.1.2011.5.25.224.3.2.11
-- 1.3.6.1.4.1.2011.5.25.224.4.2.11
		-- 1.3.6.1.4.1.2011.5.25.224.2.1.12
		hwIPSecPkiCACertValid NOTIFICATION-TYPE
			OBJECTS { hwIPSecPkiStartValidTime, hwIPSecPkiExpiredTime, hwIPSecPkiCAIssuer, hwIPSecPkiCASubject }
			STATUS current
			DESCRIPTION 
				"IPsec pki CA certificate is valid."
			::= { hwIPSecNotifications 12 }
		
--   1.3.6.1.4.1.2011.5.25.224.3.2.11
-- 1.3.6.1.4.1.2011.5.25.224.4.2.11
		-- 1.3.6.1.4.1.2011.5.25.224.2.1.13
		hwIPSecPkiCACertExpired NOTIFICATION-TYPE
			OBJECTS { hwIPSecPkiStartValidTime, hwIPSecPkiExpiredTime, hwIPSecPkiCAIssuer, hwIPSecPkiCASubject  }
			STATUS current
			DESCRIPTION 
				"IPsec pki CA certificate will be expired."
			::= { hwIPSecNotifications 13 }
		
--   1.3.6.1.4.1.2011.5.25.224.3.2.11
-- 1.3.6.1.4.1.2011.5.25.224.4.2.11
		-- 1.3.6.1.4.1.2011.5.25.224.2.1.14
		hwIPSecPkiLocalCertInValid NOTIFICATION-TYPE
			OBJECTS { hwIPSecPkiStartValidTime, hwIPSecPkiExpiredTime, hwIPSecPkiCAIssuer, hwIPSecPkiCASubject  }
			STATUS current
			DESCRIPTION 
				"IPsec pki local certificate is invalid."
			::= { hwIPSecNotifications 14 }
		
--   1.3.6.1.4.1.2011.5.25.224.3.2.11
-- 1.3.6.1.4.1.2011.5.25.224.4.2.11
		-- 1.3.6.1.4.1.2011.5.25.224.2.1.15
		hwIPSecPkiLocalCertValid NOTIFICATION-TYPE
			OBJECTS { hwIPSecPkiStartValidTime, hwIPSecPkiExpiredTime, hwIPSecPkiCAIssuer, hwIPSecPkiCASubject  }
			STATUS current
			DESCRIPTION 
				"IPsec pki local certificate is valid."
			::= { hwIPSecNotifications 15 }
		
--   1.3.6.1.4.1.2011.5.25.224.3.2.11
-- 1.3.6.1.4.1.2011.5.25.224.4.2.11
		-- 1.3.6.1.4.1.2011.5.25.224.2.1.16
		hwIPSecPkiLocalCertExpired NOTIFICATION-TYPE
			OBJECTS { hwIPSecPkiStartValidTime, hwIPSecPkiExpiredTime, hwIPSecPkiCAIssuer, hwIPSecPkiCASubject  }
			STATUS current
			DESCRIPTION 
				"IPsec pki local certificate will be expired."
			::= { hwIPSecNotifications 16 }
		
--   1.3.6.1.4.1.2011.5.25.224.3.2.11
-- 1.3.6.1.4.1.2011.5.25.224.4.2.11
		-- 1.3.6.1.4.1.2011.5.25.224.2.1.17
		hwIPSecPkiCrlInValid NOTIFICATION-TYPE
			OBJECTS { hwIPSecPkiStartValidTime, hwIPSecPkiExpiredTime, hwIPSecPkiCrlIssuer  }
			STATUS current
			DESCRIPTION 
				"IPsec pki crl is invalid."
			::= { hwIPSecNotifications 17 }
		
--   1.3.6.1.4.1.2011.5.25.224.3.2.11
-- 1.3.6.1.4.1.2011.5.25.224.4.2.11
		-- 1.3.6.1.4.1.2011.5.25.224.2.1.18
		hwIPSecPkiCrlValid NOTIFICATION-TYPE
			OBJECTS { hwIPSecPkiStartValidTime, hwIPSecPkiExpiredTime, hwIPSecPkiCrlIssuer }
			STATUS current
			DESCRIPTION 
				"IPsec pki crl is valid."
			::= { hwIPSecNotifications 18 }
		
--   1.3.6.1.4.1.2011.5.25.224.3.2.11
-- 1.3.6.1.4.1.2011.5.25.224.4.2.11
		-- 1.3.6.1.4.1.2011.5.25.224.2.1.19
		hwIPSecPkiCrlExpired NOTIFICATION-TYPE
			OBJECTS { hwIPSecPkiStartValidTime, hwIPSecPkiExpiredTime, hwIPSecPkiCrlIssuer }
			STATUS current
			DESCRIPTION 
				"IPsec pki crl will be expired."
			::= { hwIPSecNotifications 19 }
 --   1.3.6.1.4.1.2011.5.25.224.3.2.11
-- 1.3.6.1.4.1.2011.5.25.224.4.2.11
        -- 1.3.6.1.4.1.2011.5.25.224.2.1.20
        hwIPSecPkiRsaKeyRemoteInValid NOTIFICATION-TYPE
            OBJECTS { hwIPSecPkiStartValidTime, hwIPSecPkiExpiredTime, hwIPSecPkiCrlIssuer }
            STATUS current
            DESCRIPTION 
                "RSA keys in master and slave device are different."
            ::= { hwIPSecNotifications 20 }


--   1.3.6.1.4.1.2011.5.25.224.3.2.11
-- 1.3.6.1.4.1.2011.5.25.224.4.2.11
        -- 1.3.6.1.4.1.2011.5.25.224.2.1.21
        hwIPSecPkiKeyUpdateInValid NOTIFICATION-TYPE
            OBJECTS { hwIPSecPkiStartValidTime, hwIPSecPkiExpiredTime, hwIPSecPkiCrlIssuer }
            STATUS current
            DESCRIPTION 
                "Automatically updating certificates failed."
            ::= { hwIPSecNotifications 21 }


--   1.3.6.1.4.1.2011.5.25.224.3.2.11
-- 1.3.6.1.4.1.2011.5.25.224.4.2.11
        -- 1.3.6.1.4.1.2011.5.25.224.2.1.22
        hwIPSecPkiKeyUpdateValid NOTIFICATION-TYPE
            OBJECTS { hwIPSecPkiStartValidTime, hwIPSecPkiExpiredTime, hwIPSecPkiCrlIssuer }
            STATUS current
            DESCRIPTION 
                "Automatically updating certificates successful."
            ::= { hwIPSecNotifications 22 } 
            
--   1.3.6.1.4.1.2011.5.25.224.3.2.11
-- 1.3.6.1.4.1.2011.5.25.224.4.2.11
		-- 1.3.6.1.4.1.2011.5.25.224.2.1.23
		hwIPSecPkiCACertUnexpired NOTIFICATION-TYPE
			OBJECTS { hwIPSecPkiStartValidTime, hwIPSecPkiExpiredTime, hwIPSecPkiCAIssuer, hwIPSecPkiCASubject }
			STATUS current
			DESCRIPTION 
				"IPsec pki CA certificate has been updated."
			::= { hwIPSecNotifications 23 }
			
--   1.3.6.1.4.1.2011.5.25.224.3.2.11
-- 1.3.6.1.4.1.2011.5.25.224.4.2.11
		-- 1.3.6.1.4.1.2011.5.25.224.2.1.24
		hwIPSecPkiLocalCertUnexpired NOTIFICATION-TYPE
			OBJECTS { hwIPSecPkiStartValidTime, hwIPSecPkiExpiredTime, hwIPSecPkiCAIssuer, hwIPSecPkiCASubject }
			STATUS current
			DESCRIPTION 
				"IPsec pki local certificate has been updated."
			::= { hwIPSecNotifications 24 } 
			
--   1.3.6.1.4.1.2011.5.25.224.3.2.11
-- 1.3.6.1.4.1.2011.5.25.224.4.2.11
		-- 1.3.6.1.4.1.2011.5.25.224.2.1.25
		hwIPSecPkiCrlUnexpired NOTIFICATION-TYPE
			OBJECTS { hwIPSecPkiStartValidTime, hwIPSecPkiExpiredTime, hwIPSecPkiCrlIssuer }
			STATUS current
			DESCRIPTION 
				"IPsec pki crl has been updated."
			::= { hwIPSecNotifications 25 }

-- 1.3.6.1.4.1.2011.5.25.224.2.1.26
		hwIPSecPKIWriteToCFFail  NOTIFICATION-TYPE
			STATUS current
			DESCRIPTION
					"The file is written to the cfcard unsuccessfully."  
			::= { hwIPSecNotifications 26 }   
			
-- 1.3.6.1.4.1.2011.5.25.224.2.1.27
		hwIPSecPKIWriteToCFSuccess  NOTIFICATION-TYPE
			STATUS current
			DESCRIPTION
					"The file is written to the cfcard successfully."  
			::= { hwIPSecNotifications 27 }


--   1.3.6.1.4.1.2011.5.25.224.2
-- 1.3.6.1.4.1.2011.5.25.224.2
		-- 1.3.6.1.4.1.2011.5.25.224.3
		hwIPSecGroup OBJECT IDENTIFIER ::= { hwIPSecMIB 3 }
		
--   1.3.6.1.4.1.2011.5.25.224.2.1
-- 1.3.6.1.4.1.2011.5.25.224.3.1
		-- 1.3.6.1.4.1.2011.5.25.224.3.1
		hwIPSecScalarGroup OBJECT-GROUP
			OBJECTS { hwIPSecIkeSaTimeout, hwIPSecIkeSaInterval, hwIPSecIkeUndoLocalname, hwIPSecIkeLocalname, hwIPSecIkeSaNatInterval, 
				hwIPSecSecSaGlobalDurationTraffic, hwIPSecSecSaGlobalDurationTimebased, hwIPSecSecPreCheck, hwIPSecSecSucceedCheck, hwIPSecSecGlobalFragmentation, 
				hwIPSecSecGlobalFilterPolicyImportAcl, hwIPSecPkiCrlChkEnable, hwIPSecPkiFileFmt, hwIPSecSecGlobalFilterPolicyExportAcl, hwIPSecSecGlobalDfBitClear
				 }
			STATUS current
			DESCRIPTION 
				"Description."
			::= { hwIPSecGroup 1 }
		
--   1.3.6.1.4.1.2011.5.25.224.2.2
-- 1.3.6.1.4.1.2011.5.25.224.3.2
		-- 1.3.6.1.4.1.2011.5.25.224.3.2
		hwIPSecBindSlotGroup OBJECT-GROUP
			OBJECTS { hwIPSecBindSlotID, hwIPSecBackupID, hwIpsecInstanceActiveSlotNum, hwIPSecBindSlotRowStatus, hwIPSecSlotBindInstanceID, 
				hwIpsecInstanceStatus }                                          
			STATUS current
			DESCRIPTION 
				"Description."
			::= { hwIPSecGroup 2 }
		
--   1.3.6.1.4.1.2011.5.25.224.2.3
-- 1.3.6.1.4.1.2011.5.25.224.3.3
		-- 1.3.6.1.4.1.2011.5.25.224.3.3
		hwIPSecRemoteTrackGroup OBJECT-GROUP
			OBJECTS { hwIPSecPeerInstanceID, hwIPSecPeerAddr, hwIPSecSourceAddr, hwIPSecEndPort, hwIPSecStartPort, 
				hwIpsecTrackInterfaceName, hwIPSecPeerRowStatus }
			STATUS current
			DESCRIPTION 
				"Description."
			::= { hwIPSecGroup 3 }
		
--   1.3.6.1.4.1.2011.5.25.224.2.4
-- 1.3.6.1.4.1.2011.5.25.224.3.4
		-- 1.3.6.1.4.1.2011.5.25.224.3.4
		hwIPSecBindVrrpGroup OBJECT-GROUP
			OBJECTS { hwIPSecVrrpInstanceID, hwIPSecVrrpInterfaceName, hwIPSecVrrpVrid, hwIPSecVrrpRowStatus }
			STATUS current
			DESCRIPTION 
				"Description."
			::= { hwIPSecGroup 4 }
		
--   1.3.6.1.4.1.2011.5.25.224.2.4
-- 1.3.6.1.4.1.2011.5.25.224.3.4
		-- 1.3.6.1.4.1.2011.5.25.224.3.5
		hwIPSecLeastActSlotGroup OBJECT-GROUP
			OBJECTS { hwIPSecLASInstanceID, hwIPSecLASlotNum, hwIPSecLASRowStatus }
			STATUS current
			DESCRIPTION 
				"Description."
			::= { hwIPSecGroup 5 }
		
--   1.3.6.1.4.1.2011.5.25.224.2.5
-- 1.3.6.1.4.1.2011.5.25.224.3.5
		-- 1.3.6.1.4.1.2011.5.25.224.3.6
		hwIPSecIkeProposalGroup OBJECT-GROUP
			OBJECTS { hwIPSecIkeProposalNumber, hwIPSecIkeProposalAuthenmethod, hwIPSecIkeProposalnAuthenAlgorithm, hwIPSecIkeProposalIntegrityAlgorithm, hwIPSecIkeProposalEncrypationAlgorithm, 
				hwIPSecIkeProposaldh, hwIPSecIkeProposalSaDuration, hwIPSecIkeProposalReAuthentication, hwIPSecIkeProposalRowStatus }
			STATUS current
			DESCRIPTION 
				"Description."
			::= { hwIPSecGroup 6 }
		
--   1.3.6.1.4.1.2011.5.25.224.2.6
-- 1.3.6.1.4.1.2011.5.25.224.3.6
		-- 1.3.6.1.4.1.2011.5.25.224.3.7
		hwIPSecIkePeerGroup OBJECT-GROUP
			OBJECTS { hwIPSecIkePeerName, hwIPSecIkePeerPresharedKeyEnable, hwIPSecIkePeerPresharedKey, hwIPSecIkePeerVpninstanceEnable, hwIPSecIkePeerVpninstance, 
				hwIPSecIkePeerRemoteLowAddr, hwIPSecIkePeerRemoteHighAddr, hwIPSecIkePeerRemoteAuthAddr, hwIPSecIkePeerRemoteIppool, hwIPSecIkePeerRemoteVpnInstance, 
				hwIPSecIkePeerRemoteNameEnable, hwIPSecIkePeerRemoteName, hwIPSecIkePeerExchangeMode, hwIPSecIkePeerNatTraversal, hwIPSecIkePeerProposalNum, 
				hwIPSecIkePeerVersionName, hwIPSecIkePeerRowStatus, hwIPSecIkePeerRemoteAuthEndAddr, hwIPSecIkePeerLocalIdtype }
			STATUS current
			DESCRIPTION 
				"Description."
			::= { hwIPSecGroup 7 }
		
--   1.3.6.1.4.1.2011.5.25.224.2.7
-- 1.3.6.1.4.1.2011.5.25.224.3.7
		-- 1.3.6.1.4.1.2011.5.25.224.3.8
		hwIPSecIkeDpdGroup OBJECT-GROUP
			OBJECTS { hwIPSecIkeDpdIndex, hwIPSecIkeDpdIntervalDemand, hwIPSecIkeDpdCheckInterval, hwIPSecIkeDpdRetryInterval, hwIPSecIkeDpdRowStatus
				 }
			STATUS current
			DESCRIPTION 
				"Description."
			::= { hwIPSecGroup 8 }
		
--   1.3.6.1.4.1.2011.5.25.224.2.8
-- 1.3.6.1.4.1.2011.5.25.224.3.8
		-- 1.3.6.1.4.1.2011.5.25.224.3.9
		hwIPSecSecProposalGroup OBJECT-GROUP
			OBJECTS { hwIPSecSecProposalName, hwIPSecSecProposalEncapmode, hwIPSecSecProposalTransform, hwIPSecSecProposalAhAuthenAlgorithm, hwIPSecSecProposalEspauthenalgorithm, 
				hwIPSecSecProposalEspEncryptAlgorithm, hwIPSecSecProposalRowStatus }
			STATUS current
			DESCRIPTION 
				"Description."
			::= { hwIPSecGroup 9 }
		
--   1.3.6.1.4.1.2011.5.25.224.2.9
-- 1.3.6.1.4.1.2011.5.25.224.3.9
		-- 1.3.6.1.4.1.2011.5.25.224.3.10
		hwIPSecSecPolicyIsakmpGroup OBJECT-GROUP
			OBJECTS { hwIPSecSecPolicyIsakmpOrTemp, hwIPSecSecPolicyIsakmpName, hwIPSecSecPolicyIsakmpSeqNumber, hwIPSecSecPolicyIsakmpSecurAclNumber, hwIPSecSecPolicyIsakmpProposalNameEnable, 
				hwIPSecSecPolicyIsakmpProposalName, hwIPSecSecPolicyIsakmpFragmentBfEncrypt, hwIPSecSecPolicyIsakmpDfBit, hwIPSecSecPolicyIsakmpSpdLimitInbnd, hwIPSecSecPolicyIsakmpSpdLimitOutbnd, 
				hwIPSecSecPolicyIsakmpDscpInbnd, hwIPSecSecPolicyIsakmpDscpOutbnd, hwIPSecSecPolicyIsakmpIkePeernameEnable, hwIPSecSecPolicyIsakmpIkePeername, hwIPSecSecPolicyIsakmpLocaladdressEnable, 
				hwIPSecSecPolicyIsakmpLocaladdress, hwIPSecSecPolicyIsakmpPfs, hwIPSecSecPolicyIsakmpTrafficBased, hwIPSecSecPolicyIsakmpTimeBased, hwIPSecSecPolicyIsakmpLogEnable, 
				hwIPSecSecPolicyIsakmpRowStatus, hwIPSecSecPolicyIsakmpSetDscpInEnable, hwIPSecSecPolicyIsakmpSetDscpOutEnable }
			STATUS current
			DESCRIPTION 
				"Description."
			::= { hwIPSecGroup 10 }
		
--   1.3.6.1.4.1.2011.5.25.224.2.11
-- 1.3.6.1.4.1.2011.5.25.224.3.10
		-- 1.3.6.1.4.1.2011.5.25.224.3.11
		hwIPSecSecPolicyIsakmpTempGroup OBJECT-GROUP
			OBJECTS { hwIPSecSecPolicyIsakmpTempRowStatus, hwIPSecSecPolicyIsakmpTempIsakmpName, hwIPSecSecPolicyIsakmpTempIsakmpSeqNumber, hwIPSecSecPolicyIsakmpTempTemplateName }
			STATUS current
			DESCRIPTION 
				"Description."
			::= { hwIPSecGroup 11 }
		
--   1.3.6.1.4.1.2011.5.25.224.2.12
-- 1.3.6.1.4.1.2011.5.25.224.3.11
		-- 1.3.6.1.4.1.2011.5.25.224.3.12
		hwIPSecSecTunnelGroup OBJECT-GROUP
			OBJECTS { hwIPSecSecTunnelName, hwIPSecSecTunnelPolicynameEanble, hwIPSecSecTunnelPolicyname, hwIPSecSecTunnelImportFilterPolicy, hwIPSecSecTunnelOutportFilterPolicy, 
				hwIPSecUndoServiceRoute, hwIPSecPortObserverIndex, hwIPSecSecTunnelInstanceId, hwIPSecSecTunnelRowStatus, hwIPSecPortMirrorInEnable, 
				hwIPSecPortMirrorOutEnable, hwIPSecPortMirrorInAcl, hwIPSecPortMirrorOutAcl }
			STATUS current
			DESCRIPTION 
				"Description."
			::= { hwIPSecGroup 12 }
		
--  1.3.6.1.4.1.2011.5.25.224.3.12
		-- 1.3.6.1.4.1.2011.5.25.224.3.13
		hwIPSecPkiEntityGroup OBJECT-GROUP
			OBJECTS { hwIPSecPkiEntityName, hwIPSecPkiEntityCmmNameEnable, hwIPSecPkiEntityCmmName, hwIPSecPkiEntityCountryEnable, hwIPSecPkiEntityCountry, 
				hwIPSecPkiEntityEmailEnable, hwIPSecPkiEntityEmail, hwIPSecPkiEntityFqdnEnable, hwIPSecPkiEntityFqdn, hwIPSecPkiEntityIpAddrEnable, 
				hwIPSecPkiEntityIpAddr, hwIPSecPkiEntityLocalityEnable, hwIPSecPkiEntityLocality, hwIPSecPkiEntityOrgEnable, hwIPSecPkiEntityOrg, 
				hwIPSecPkiEntityOrgUnitEnable, hwIPSecPkiEntityOrgUnit, hwIPSecPkiEntityStateEnable, hwIPSecPkiEntityState, hwIPSecPkiEntityRowStatus
				 }
			STATUS current
			DESCRIPTION 
				"Description."
			::= { hwIPSecGroup 13 }
		
--  1.3.6.1.4.1.2011.5.25.224.3.13
		-- 1.3.6.1.4.1.2011.5.25.224.3.14
		hwIPSecPkiDomainGroup OBJECT-GROUP
			OBJECTS { hwIPSecPkiDomainName, hwIPSecPkiDomainCertReqEntityEnable, hwIPSecPkiDomainCertReqEntity, hwIPSecPkiDomainCrlAutoUpdateEnable, hwIPSecPkiDomainCrlMethod, 
				hwIPSecPkiDomainCrlUrl, hwIPSecPkiDomainCrlLdapAttr, hwIPSecPkiDomainCrlLdapDn, hwIPSecPkiDomainCrlUpdatePeriod, hwIPSecPkiDomainLSAuthenName, 
				hwIPSecPkiDomainLSAuthenPWD, hwIPSecPkiDomainLSIp, hwIPSecPkiDomainLSPort, hwIPSecPkiDomainLSVersion, hwIPSecPkiDomainLSSource, 
				hwIPSecPkiDomainRowStatus, hwIPSecPkiDomainUndoLdapServer, hwIPSecPkiDomainUndoCrlLdapDnAll, hwIPSecPkiDomainUndoCrlLdapDn, hwIPSecPkiDomainUndoCrlUrlAll, 
				hwIPSecPkiDomainUndoCrlUrl }
			STATUS current
			DESCRIPTION 
				"Description."
			::= { hwIPSecGroup 14 }
		
--  1.3.6.1.4.1.2011.5.25.224.3.14
		-- 1.3.6.1.4.1.2011.5.25.224.3.15
		hwIPSecPkiCerAttrGrpGroup OBJECT-GROUP
			OBJECTS { hwIPSecPkiCerAttrGrpName, hwIPSecPkiCerAttrGrpMode, hwIPSecPkiCerAttrGrpOperate, hwIPSecPkiCerAttrGrpValue, hwIPSecPkiCerAttrGrpIp, 
				hwIPSecPkiCerAttrGrpRowStatus, hwIPSecPkiCerAttrGrpPolicyId }
			STATUS current
			DESCRIPTION 
				"Description."
			::= { hwIPSecGroup 15 }
		
--  1.3.6.1.4.1.2011.5.25.224.3.15
		-- 1.3.6.1.4.1.2011.5.25.224.3.16
		hwIPSecPkiCerAccCtlPolicyGroup OBJECT-GROUP
			OBJECTS { hwIPSecPkiCerAccCtlPolicyName, hwIPSecPkiCerAccCtlPolicyId, hwIPSecPkiCerAccCtlPolicyMode, hwIPSecPkiCerAccCtlPolicyAttrGrpName, hwIPSecPkiCerAccCtlPolicyRowStatus
				 }
			STATUS current
			DESCRIPTION 
				"Description."
			::= { hwIPSecGroup 16 }
		
--  1.3.6.1.4.1.2011.5.25.224.3.15
		-- 1.3.6.1.4.1.2011.5.25.224.3.17
		hwIPSecEnableSlotGroup OBJECT-GROUP
			OBJECTS { hwIPSecSlotIndex, hwIPSecSlotID, hwIPSecEnable, hwIPSecEnableRowStatus }
			STATUS current
			DESCRIPTION 
				"Description."
			::= { hwIPSecGroup 17 }
		
		-- 1.3.6.1.4.1.2011.5.25.224.3.18
		hwIPSecInstanceGroup OBJECT-GROUP
			OBJECTS { hwIPSecInstanceID, hwIPSecInstanceEnable, hwIPSecInstanceRowStatus }
			STATUS current
			DESCRIPTION 
				"Description."
			::= { hwIPSecGroup 18 }
		
--  1.3.6.1.4.1.2011.5.25.224.3.16
		-- 1.3.6.1.4.1.2011.5.25.224.3.19
		hwIPSecPkiNotifyVarGroup OBJECT-GROUP
			OBJECTS { hwIPSecPolicyName, hwIPSecPolicySeq, hwIPSecInterface, hwIPSecLocalIp, hwIPSecRemoteIp, 
				hwIPSecRemotePort, hwIPSecPkiGetCertUrl, hwIPSecPkiGetCertIp, hwIPSecPkiGetCertPort, hwIPSecPkiCertAttr, 
				hwIPSecPkiCertDiffName, hwIPSecPkiCAIssuer, hwIPSecPkiCASubject, hwIPSecPkiCrlIssuer, hwIPSecPkiGetCertLdapVersion, 
				hwIPSecPkiExpiredTime, hwIPSecPkiStartValidTime }
			STATUS current
			DESCRIPTION 
				"Description."
			::= { hwIPSecGroup 19 }
		
--  1.3.6.1.4.1.2011.5.25.224.3.18
		-- 1.3.6.1.4.1.2011.5.25.224.3.20
		hwIPSecPkiNotifyEventGroup NOTIFICATION-GROUP
			NOTIFICATIONS { hwIPSecTunnelStateUp, hwIPSecTunnelStateDown, hwIPSecPkiHttpGetCrlSuccess, hwIPSecPkiHttpGetCrlFail, hwIPSecPkiLdapGetCrlSuccess, 
				hwIPSecPkiLdapGetCrlFail, hwIPSecPkiHttpGetCertSuccess, hwIPSecPkiHttpGetCertFail, hwIPSecPkiLdapGetCertSuccess, hwIPSecPkiLdapGetCertFail, 
				hwIPSecPkiCACertInValid, hwIPSecPkiCACertValid, hwIPSecPkiCACertExpired, hwIPSecPkiLocalCertInValid, hwIPSecPkiLocalCertValid, 
				hwIPSecPkiLocalCertExpired, hwIPSecPkiCrlInValid, hwIPSecPkiCrlValid, hwIPSecPkiCrlExpired,hwIPSecPkiRsaKeyRemoteInValid, hwIPSecPkiKeyUpdateInValid,
				hwIPSecPkiKeyUpdateValid, hwIPSecPkiCACertUnexpired, hwIPSecPkiLocalCertUnexpired, hwIPSecPkiCrlUnexpired,hwIPSecPKIWriteToCFFail,hwIPSecPKIWriteToCFSuccess}
			STATUS current
			DESCRIPTION 
				"Description."
			::= { hwIPSecGroup 20 }
	
--  1.3.6.1.4.1.2011.5.25.224.3.21
		-- 1.3.6.1.4.1.2011.5.25.224.3.21
		hwIPSecPerformanceMonitorGroup OBJECT-GROUP
			OBJECTS { hwIPSecMonitorSlotID, hwIPSecMonitorCpuID, hwIPSecMonitorVcpuUsage, 
				hwIPSecMonitorShorterThan64Bytes, hwIPSecMonitor64To127Bytes, hwIPSecMonitor128To191Bytes, hwIPSecMonitor192To255Bytes, hwIPSecMonitor256To319Bytes, 
				hwIPSecMonitor320To383Bytes, hwIPSecMonitor384To447Bytes, hwIPSecMonitor448To511Bytes, hwIPSecMonitor512To575Bytes, hwIPSecMonitor576To639Bytes, 
				hwIPSecMonitor640To703Bytes, hwIPSecMonitor704To767Bytes, hwIPSecMonitor768To831Bytes, hwIPSecMonitor832To895Bytes,hwIPSecMonitor896To959Bytes, hwIPSecMonitor960To1023Bytes,
				hwIPSecMonitor1024To1500Bytes, hwIPSecMonitorLongerThan1500Bytes,
				hwIPSecMonitorTotalBytes}
			STATUS current
			DESCRIPTION 
				"Description."
			::= { hwIPSecGroup 21 }

--  1.3.6.1.4.1.2011.5.25.224.3.22
		-- 1.3.6.1.4.1.2011.5.25.224.3.22
		hwIPSecMulBoardPerformanceMonitorGroup OBJECT-GROUP
			OBJECTS { hwIPSecMulBoardMonitorSlotIDStr, hwIPSecMulBoardMonitorCpuID, hwIPSecMulBoardMonitorVcpuUsage,
				hwIPSecMulBoardMonitorShorterThan64Bytes, hwIPSecMulBoardMonitor64To127Bytes, hwIPSecMulBoardMonitor128To191Bytes, hwIPSecMulBoardMonitor192To255Bytes,          
                                                                             hwIPSecMulBoardMonitor256To319Bytes, hwIPSecMulBoardMonitor320To383Bytes, hwIPSecMulBoardMonitor384To447Bytes, hwIPSecMulBoardMonitor448To511Bytes, 
                                                                             hwIPSecMulBoardMonitor512To575Bytes, hwIPSecMulBoardMonitor576To639Bytes, hwIPSecMulBoardMonitor640To703Bytes, hwIPSecMulBoardMonitor704To767Bytes, 
                                                                             hwIPSecMulBoardMonitor768To831Bytes, hwIPSecMulBoardMonitor832To895Bytes,hwIPSecMulBoardMonitor896To959Bytes, hwIPSecMulBoardMonitor960To1023Bytes,
				hwIPSecMulBoardMonitor1024To1500Bytes, hwIPSecMulBoardMonitorLongerThan1500Bytes,
				hwIPSecMulBoardMonitorTotalBytes}
			STATUS current
			DESCRIPTION 
				"Description."
			::= { hwIPSecGroup 22 }
				
		-- 1.3.6.1.4.1.2011.5.25.224.4  
		hwIPSecCompliances OBJECT IDENTIFIER ::= { hwIPSecMIB 4 }
	
		hwIPSecCompliance MODULE-COMPLIANCE
			STATUS current
			DESCRIPTION 
				"The compliance statement for systems supporting 
				the HUAWEI-IPSEC-MIB."
			MODULE 
				MANDATORY-GROUPS { hwIPSecScalarGroup, hwIPSecBindSlotGroup, hwIPSecRemoteTrackGroup,
					hwIPSecBindVrrpGroup, hwIPSecLeastActSlotGroup, hwIPSecIkeProposalGroup,
					hwIPSecIkePeerGroup, hwIPSecIkeDpdGroup, hwIPSecSecProposalGroup,
					hwIPSecSecPolicyIsakmpGroup, hwIPSecSecPolicyIsakmpTempGroup, hwIPSecSecTunnelGroup,
					hwIPSecPkiEntityGroup, hwIPSecPkiDomainGroup, hwIPSecPkiCerAttrGrpGroup,
					hwIPSecPkiCerAccCtlPolicyGroup, hwIPSecEnableSlotGroup, hwIPSecInstanceGroup,
					hwIPSecPkiNotifyVarGroup, hwIPSecPkiNotifyEventGroup, hwIPSecPerformanceMonitorGroup, hwIPSecMulBoardPerformanceMonitorGroup}
		::= { hwIPSecCompliances 1 }
	
	END

--
-- HUAWEI-IPSEC-MIB_0316.mib
--
