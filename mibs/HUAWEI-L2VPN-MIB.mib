-- HUAWEI-L2VPN-MIB.mib
--  ==================================================================
-- Copyright (C) 2014 by  HUAWEI TECHNOLOGIES. All rights reserved.
-- 
-- Description: HUAWEI L2VPN Management MIB
-- Reference:
-- Version:     V2.02
-- History:
--              V1.0 WangSongTao, 2009-02-26, publish 
-- ==================================================================
    
    HUAWEI-L2VPN-MIB DEFINITIONS ::= BEGIN
    
        IMPORTS
            hwDatacomm           
                FROM HUAWEI-MIB
                    EnabledStatus
                FROM P-BRIDGE-MIB
                    OBJECT-GROUP, MODULE-COMPLIANCE
                FROM SNMPv2-CONF                 
                    sysUpTime         
                FROM SNMPv2-MIB
                    OBJECT-TYPE, MODULE-IDENTITY, Unsigned32
                FROM SNMPv2-SMI;
        
        -- 1.3.6.1.4.1.2011.5.25.119.8
            hwL2VpnAttribute MODULE-IDENTITY 
                LAST-UPDATED "201406181000Z"               -- June 18, 2014 at 10:00 GMT
                ORGANIZATION
                     "Huawei Technologies Co.,Ltd."
                CONTACT-INFO 
                     "Huawei Industrial Base
                       Bantian, Longgang
                        Shenzhen 518129
                        People's Republic of China
                        Website: http://www.huawei.com
                        Email: support@huawei.com
                      "
                DESCRIPTION
                     "The HUAWEI-L2VPN-MIB contains objects to
                      manage global Attributes of L2VPN."
                
                REVISION "201406181000Z"                    -- June 18, 2014 at 10:00 GMT
                DESCRIPTION
                     "Add 11 leaf nodes to hwL2VpnAttribute."

                REVISION "201503161750Z"                    -- Mar 16, 2015 at 17:50 GMT
                DESCRIPTION
                     "Add 1 leaf nodes to hwL2VpnAttribute."
                                           
                ::= { hwL2Vpn 8 }                
-- 
-- Node definitions
-- 
  
        -- 1.3.6.1.4.1.2011.5.25.119
        hwL2Vpn OBJECT IDENTIFIER ::= { hwDatacomm 119 }
                
--         
-- The Global Attributes Group of The mpls L2vpn
-- 
  
-- 
-- The Leaf Nodes of hwL2VpnAttribute
-- 
        -- 1.3.6.1.4.1.2011.5.25.119.8.1
        hwL2VpnEnable OBJECT-TYPE
            SYNTAX EnabledStatus
            MAX-ACCESS read-write
            STATUS current
            DESCRIPTION
                "This object indicates whether enabled mpls L2vpn capability or not."
            ::= { hwL2VpnAttribute 1 }                
            
        -- 1.3.6.1.4.1.2011.5.25.119.8.2
        hwL2VpnWorkingMode OBJECT-TYPE
            SYNTAX INTEGER
                {
                pwe3(1),
                martini(2),
                unknown(3)
                }
            MAX-ACCESS read-write
            STATUS current
            DESCRIPTION
                "This object indicates the working mode of mpls L2vpn."
            ::= { hwL2VpnAttribute 2 }

        -- 1.3.6.1.4.1.2011.5.25.119.8.4
        hwL2VpnLocalCCCNumber OBJECT-TYPE
            SYNTAX Unsigned32
            MAX-ACCESS read-only
            STATUS current
            DESCRIPTION
                "This object indicates the local ccc number have created."
            ::= { hwL2VpnAttribute 4 }

        -- 1.3.6.1.4.1.2011.5.25.119.8.5
        hwL2VpnRemoteCCCNumber OBJECT-TYPE
            SYNTAX Unsigned32
            MAX-ACCESS read-only
            STATUS current
            DESCRIPTION
                "This object indicates the remote ccc number have created."
            ::= { hwL2VpnAttribute 5 }

        -- 1.3.6.1.4.1.2011.5.25.119.8.6
        hwL2VpnSvcNumber OBJECT-TYPE
            SYNTAX Unsigned32
            MAX-ACCESS read-only
            STATUS current
            DESCRIPTION
                "This object indicates the static vc number have created."
            ::= { hwL2VpnAttribute 6 }

        -- 1.3.6.1.4.1.2011.5.25.119.8.7
        hwL2VpnLdpVcNumber OBJECT-TYPE
            SYNTAX Unsigned32
            MAX-ACCESS read-only
            STATUS current
            DESCRIPTION
                "This object indicates the ldp vc number have created."
            ::= { hwL2VpnAttribute 7 }

        -- 1.3.6.1.4.1.2011.5.25.119.8.8
        hwL2VpnBgpVcNumber OBJECT-TYPE
            SYNTAX Unsigned32
            MAX-ACCESS read-only
            STATUS current
            DESCRIPTION
                "This object indicates the bgp vc number have created."
            ::= { hwL2VpnAttribute 8 }

        -- 1.3.6.1.4.1.2011.5.25.119.8.9
        hwL2VpnVsiNumber OBJECT-TYPE
            SYNTAX Unsigned32
            MAX-ACCESS read-only
            STATUS current
            DESCRIPTION
                "This object indicates the vsi number have created."
            ::= { hwL2VpnAttribute 9 }

         -- 1.3.6.1.4.1.2011.5.25.119.8.10
        hwL2VpnBgpVsiNumber OBJECT-TYPE
            SYNTAX Unsigned32
            MAX-ACCESS read-only
            STATUS current
            DESCRIPTION
                "This object indicates the bgp vsi number have created."
            ::= { hwL2VpnAttribute 10 }

         -- 1.3.6.1.4.1.2011.5.25.119.8.11
        hwL2VpnVsiVcNumber OBJECT-TYPE
            SYNTAX Unsigned32
            MAX-ACCESS read-only
            STATUS current
            DESCRIPTION
                "This object indicates the vsi vc number have created."
            ::= { hwL2VpnAttribute 11 }

         -- 1.3.6.1.4.1.2011.5.25.119.8.12
        hwVplsVcNumberMaxNum OBJECT-TYPE
            SYNTAX Unsigned32
            MAX-ACCESS accessible-for-notify
            STATUS current
            DESCRIPTION
                "This object indicates the max vpls vc number."
            ::= { hwL2VpnAttribute 12 }

         -- 1.3.6.1.4.1.2011.5.25.119.8.13
        hwVplsVcNumberUpperThreshold OBJECT-TYPE
            SYNTAX Unsigned32
            MAX-ACCESS accessible-for-notify
            STATUS current
            DESCRIPTION
                "This object indicates the vpls vc number is upper than threshold."
            ::= { hwL2VpnAttribute 13 }  
            
         -- 1.3.6.1.4.1.2011.5.25.119.8.14
        hwL2VpnVcLimitClass OBJECT-TYPE
            SYNTAX INTEGER
            {
                vll(1),
                vpls(2)
            }
            MAX-ACCESS accessible-for-notify
            STATUS current
            DESCRIPTION
                "This object indicates the class of l2vpn vc limit."
            ::= { hwL2VpnAttribute 14 }  
        
          -- 1.3.6.1.4.1.2011.5.25.119.8.15
        hwL2VpnSwitchVcNumber OBJECT-TYPE
            SYNTAX Unsigned32
            MAX-ACCESS read-only
            STATUS current
            DESCRIPTION
                "This object indicates the number of MS-PWs already created."
            ::= { hwL2VpnAttribute 15 }                                           
-- 
--  Conformance information
-- 
        -- 1.3.6.1.4.1.2011.5.25.119.8.3
        hwL2VpnMIBConformance OBJECT IDENTIFIER ::= { hwL2VpnAttribute 3 }
        
        -- 1.3.6.1.4.1.2011.5.25.119.8.3.1
        hwL2VpnMIBCompliances OBJECT IDENTIFIER ::= { hwL2VpnMIBConformance 1 }
        
-- this module
        -- 1.3.6.1.4.1.2011.5.25.119.8.3.1.1
        hwL2VpnMIBCompliance MODULE-COMPLIANCE
            STATUS current
            DESCRIPTION 
                "The compliance statement for systems supporting
                 the HUAWEI-L2VPN-MIB."
            MODULE -- this module
            MANDATORY-GROUPS { hwL2VpnMIBGroup }
            ::= { hwL2VpnMIBCompliances 1 }
        
        -- 1.3.6.1.4.1.2011.5.25.119.8.3.2
        hwL2VpnMIBGroups OBJECT IDENTIFIER ::= { hwL2VpnMIBConformance 2 }
        
        -- 1.3.6.1.4.1.2011.5.25.119.8.3.2.1
        hwL2VpnMIBGroup OBJECT-GROUP
            OBJECTS { hwL2VpnEnable, hwL2VpnWorkingMode, hwL2VpnLocalCCCNumber, hwL2VpnRemoteCCCNumber, hwL2VpnSvcNumber, hwL2VpnLdpVcNumber, hwL2VpnBgpVcNumber,hwL2VpnVsiNumber,hwL2VpnBgpVsiNumber,hwL2VpnVsiVcNumber,hwVplsVcNumberMaxNum,hwVplsVcNumberUpperThreshold,hwL2VpnVcLimitClass,hwL2VpnSwitchVcNumber }
            STATUS current
            DESCRIPTION 
                "The L2VPN's attributes group."
            ::= { hwL2VpnMIBGroups 1 }                
 
        END

--
-- HUAWEI-L2VPN-MIB.mib
--
