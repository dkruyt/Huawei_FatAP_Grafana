-- ============================================================================
-- Copyright (C) 2016 by  HUAWEI TECHNOLOGIES. All rights reserved.
-- Description: The mib is used for configuration.
-- Reference: 
-- Version: V1.36
-- ============================================================================
-- Module definition

	HUAWEI-WLAN-CONFIGURATION-MIB DEFINITIONS ::= BEGIN

		IMPORTS
			hwWlan
				FROM HUAWEI-WLAN-MIB
		        hwWlanApName
		                FROM HUAWEI-WLAN-AP-MIB      
		        hwWlanRadioID
		                FROM HUAWEI-WLAN-AP-RADIO-MIB
			OBJECT-GROUP, MODULE-COMPLIANCE, NOTIFICATION-GROUP
				FROM SNMPv2-CONF
			IpAddress, Integer32, Unsigned32, Counter64, OBJECT-TYPE,
			MODULE-IDENTITY, NOTIFICATION-TYPE
				FROM SNMPv2-SMI
			MacAddress, RowStatus, DateAndTime
				FROM SNMPv2-TC;
		--1.3.6.1.4.1.2011.6.139.11
		hwWlanConfig MODULE-IDENTITY
			LAST-UPDATED "201603221531Z"		-- March 22, 2016 at 15:31 GMT 
			ORGANIZATION
				"Huawei Technologies Co.,Ltd."
			CONTACT-INFO
			 "Huawei Industrial Base
				   Bantian, Longgang
				   Shenzhen 518129
				   People's Republic of China
				   Website: http://www.huawei.com
				   Email: support@huawei.com
				  "
                        DESCRIPTION 
				"The MIB module defines the configuration of AP." 

                                                                REVISION "201603221531Z"		-- March 22, 2016 at 15:31 GMT 
				DESCRIPTION 
				"V1.36, Modify the range of hwAPTrafficProfileOptimizeSuppressionBc, hwAPTrafficProfileOptimizeSuppressionUc, hwAPTrafficProfileOptimizeSuppressionMc and hwCellularNetworkProfilePlmnIDList."

                                                                REVISION "201603211546Z"		-- March 21, 2016 at 15:46 GMT 
				DESCRIPTION 
				"V1.35, Add nodes for hwVapAntiAttackBroadcastFloodSwitch, hwVapAntiAttackBroadcastFloodStaRateThreshold and hwVapAntiAttackBroadcastFloodBlacklistSwitch."
				
                                                                REVISION "201603152015Z"		-- March 15, 2016 at 20:15 GMT 
				DESCRIPTION 
				"V1.34, Modify the description of hwApProfMeshRole."

			REVISION "201603101136Z"		-- March 10, 2016 at 11:36 GMT 
				DESCRIPTION 
				"V1.33, Modify the range of mib nodes."

                                                    REVISION "201602271436Z"		-- Feb 27, 2016 at 14:36 GMT 
				DESCRIPTION 
				"V1.32, Modify the description of hwAPGrpRadioFrequency and hwAPSpRadioFrequency." 
			REVISION "201602051436Z"		-- Feb 5, 2016 at 14:36 GMT 
				DESCRIPTION 
				"V1.31, Add nodes for hwBleProfileTable, hwAPGroupCardTable, hwAPSpecificCardTable, hwIoTSerialProfileTable, hwIoTProfileTable and hwIoTProfileManagementServerTable ." 
			REVISION "201601121347Z"		-- JAN 12, 2016 at 13:47 GMT 
				DESCRIPTION 
				"V1.30, Add nodes for hwWlanIDIndexedAPSpecificTable, hwIDIndexedAPSpecificWiredPortTable, hwIDIndexedAPSpecificRadioIdTable and hwIDIndexedAPSpecificVapTable ." 
			REVISION "201512231525Z"		-- DEC 23, 2015 at 15:25 GMT 
				DESCRIPTION 
				"V1.29, Add nodes for hwAPWiredPortProfileTable and hwAPPortLinkProfileTable." 
            REVISION "201512172024Z"		-- DEC 17, 2015 at 20:24 GMT 
				DESCRIPTION 
				"V1.28, Modify nodes for hwAPWiredPortProfilePortMode , hwAPGrpWPInterfaceNum, hwAPSpWPInterfaceNum, hwWlanApDataCollectionInterval." 				
            REVISION "201511211025Z"		-- NOV 21, 2015 at 10:25 GMT 
				DESCRIPTION 
				"V1.27, Add nodes for hwApSystemProfileTable and hwAPPortLinkProfileTable." 
            REVISION "201510292030Z"		-- Oct 29, 2015 at 20:30 GMT 
				DESCRIPTION 
				"V1.26, Modify the range of mib nodes."
			REVISION "201510101030Z"		-- Oct 10, 2015 at 10:30 GMT 
				DESCRIPTION 
				"V1.25, Modify the range of mib nodes."
			REVISION "201509251030Z"		-- Sept 25, 2015 at 10:30 GMT 
				DESCRIPTION 
				"V1.24, Modify the range of hwSsidClientEdcaVoiceTXOPLimit."
			REVISION "201509151030Z"		-- Sept 15, 2015 at 10:30 GMT 
				DESCRIPTION 
				"V1.23, Add invalid parameter in the hwAPSpecificRadioTable."
			REVISION "201508261530Z"		-- August 26, 2015 at 15:30 GMT
    			DESCRIPTION 
				"V1.22, Modify the nodes of HUAWEI-WLAN-CONFIGURATION-MIB file." 
			REVISION "201508051530Z"		-- August 5, 2015 at 15:30 GMT
    			DESCRIPTION 
				"V1.21, Modify the nodes of HUAWEI-WLAN-CONFIGURATION-MIB file." 
			REVISION "201508050950Z"		-- August 5, 2015 at 9:50 GMT
    			DESCRIPTION 
				"V1.20, Modify the nodes of HUAWEI-WLAN-CONFIGURATION-MIB file." 
			REVISION "201507230950Z"		-- July 23, 2015 at 9:50 GMT
    			DESCRIPTION 
				"V1.19, Modify the range of hwSecurityWapiAcPrvKeyFileName." 
                                                       REVISION "201507221048Z"		-- July 22, 2015 at 10:48 GMT
			DESCRIPTION
				"V1.18, Add nodes for hwVapOptinon82RidUserDefined, hwVapOptinon82RidMacFormat,hwVapOptinon82InsertCidFormat , hwVapOptinon82CidUserDefined, 
							hwVapOptinon82CidMacFormat, hwSsidBeacon2gRate, hwSsidBeacon5gRate, hwSsidDenyBroadcastProbe, hwSsidProbeResponseRetry, 
							hwSsidUapsd, hwSsidActiveDullClient, hwWlanMeshProfilePriorityMapTrustMode, hwWlanMeshProfilePriorityDscpMap80211e, 
							hwWdsProfilePriorityMapTrustMode, hwWdsProfilePriorityDscpMap80211e"
			REVISION "201507101400Z"		-- July 10, 2015 at 14:00 GMT
			DESCRIPTION
				"V1.17, Add nodes for hw2gRadioProfileRadioType,hw5gRadioProfileRadioType,hwWlanCountryCodeTable"
    			REVISION "201506231400Z"		-- June 23, 2015 at 14:00 GMT
			DESCRIPTION
				"V1.16, Add nodes for hwWlanMeshProfileTable,hwApSystemProfileTable,hwAPTrafficProfileTable,hwSoftgreProfileTable."
			REVISION "201506211040Z"		-- June 21, 2015 at 10:40 GMT
			DESCRIPTION
				"V1.15, Add nodes for report sta info."
			REVISION "201506160910Z"		-- June 16, 2015 at 9:10 GMT
			DESCRIPTION
				"V1.14, Add nodes for eirp."			
			REVISION "201506021110Z"		-- June 2, 2015 at 11:10 GMT
			DESCRIPTION
				"V1.13, Add nodes for antenna output mode."
			REVISION "201505131430Z"		-- May 13, 2015 at 14:30 GMT
			DESCRIPTION
				"V1.12, Modify the range of hwAPTrafficProfileFilterACLID."
			REVISION "201505121430Z"                               -- May 12, 2015 at 14:30 GMT 
			DESCRIPTION 
				"V1.11, Add the description of mib nodes." 
			REVISION "201505111430Z"		-- May 11, 2015 at 14:30 GMT
			DESCRIPTION
				"V1.10, Change value of hwLocationPrivateMuEnable."   
			REVISION "201505041430Z"		-- May 4, 2015 at 14:30 GMT
			DESCRIPTION
				"V1.09, Add nodes for hwWlanMeshProfileTable."   
			REVISION "201504271550Z"		-- April 27, 2015 at 15:50 GMT
			DESCRIPTION
				"V1.08, Add nodes for utmost power switch."   
			REVISION "201504231150Z"		-- April 23, 2015 at 11:50 GMT
			DESCRIPTION
				"V1.07, Add some nodes."   
			REVISION "201504200930Z"		-- April 20, 2015 at 9:30 GMT
			DESCRIPTION
				"V1.06, Modify the range of some nodes."
			REVISION "201504131015Z"		-- April 13, 2015 at 10:15 GMT
			DESCRIPTION
				"V1.05, Modify the sequence of some table's index and the range of some nodes."
			REVISION "201504101455Z"		-- April 10, 2015 at 14:55 GMT
			DESCRIPTION
				"V1.04, 1.Modify the range of hwWidsConfidentOuiWhitelistOui, hwAPGrpWidsProfile, hwAPGrpLocationProfile, hwAPGrpSpectrumProfile, 
											hwAPSp2gRadioProfile, hwAPSpDomainProfile, hwAPSp5gRadioProfile, hwAPSpWidsProfile,
											hwAPSpLocationProfile, hwAPSpSpectrumProfile, hwWidsContainProfile, hwWidsSpoofProfile, hwWidsConfidentProfile.
						2.Add hwWlanLoadBalanceStaticGroupTable.
						3.Delete the node hwRrmLoadBalanceGrpName and add node hwRrmSmartRoamType."
			REVISION "201503301835Z"		-- March 30, 2015 at 18:35 GMT
			DESCRIPTION
				"V1.02, Modify the name of the node of hwAPProvision."
		    REVISION "201503090935Z"		-- March 9, 2015 at 09:35 GMT
			DESCRIPTION
				"V1.01, Modify the range of hwApProfHighTempThreshold and hwAPWiredPortProfilePortEthTrunkID."
	                REVISION "201502021055Z"		-- February 2, 2015 at 10:55 GMT
			DESCRIPTION
				"V1.00, Inital version."
			::= { hwWlan 11 }

--
--Node definitions
--

		--1.3.6.1.4.1.2011.6.139.11.1
		hwWlanConfigObjects OBJECT IDENTIFIER ::= { hwWlanConfig 1 }

		--1.3.6.1.4.1.2011.6.139.11.1.1
		hwWlanGlobalConfig OBJECT IDENTIFIER ::= { hwWlanConfigObjects 1 }

		 --1.3.6.1.4.1.2011.6.139.11.1.1.1
		hwWlanGlobalApUsername OBJECT-TYPE
			SYNTAX OCTET STRING (SIZE (4..31))
			MAX-ACCESS read-write
			STATUS current
			DESCRIPTION 
				"This object indicates user names for Telnet-based login to APs."
			::= { hwWlanGlobalConfig 1 }

		 --1.3.6.1.4.1.2011.6.139.11.1.1.2
		hwWlanGlobalApPassword OBJECT-TYPE
			SYNTAX OCTET STRING (SIZE (8..32))
			MAX-ACCESS read-write
			STATUS current
			DESCRIPTION 
				"This object indicates passwords for Telnet-based login to APs."
			::= { hwWlanGlobalConfig 2 }

		 --1.3.6.1.4.1.2011.6.139.11.1.1.3
		hwWlanUsernamePasswordApMac OBJECT-TYPE
			SYNTAX MacAddress
			MAX-ACCESS read-write
			STATUS current
			DESCRIPTION 
				"This object indicates query and setting of MAC addresses of clients logging in to APs."
			::= { hwWlanGlobalConfig 3 }

		 --1.3.6.1.4.1.2011.6.139.11.1.1.4
		hwWlanGlobalApLldpSwitch OBJECT-TYPE
			SYNTAX INTEGER
				{
				disable(1) ,
				enable(2)
				}
			MAX-ACCESS read-write
			STATUS current
			DESCRIPTION 
				"This object indicates the status of the global LLDP function. The default value is 2."
			::= { hwWlanGlobalConfig 4 }

		 --1.3.6.1.4.1.2011.6.139.11.1.1.5
		hwWlanGlobalIpv6Enable OBJECT-TYPE
			SYNTAX INTEGER
				{
				disable(1),
				enable(2)
				}
			MAX-ACCESS read-write
			STATUS current
			DESCRIPTION 
				"This object indicates the status of the global IPv6 function. The default value is 1."
			::= { hwWlanGlobalConfig 5 }

		 --1.3.6.1.4.1.2011.6.139.11.1.1.6
		hwWlanStationIpv6Enable OBJECT-TYPE
			SYNTAX INTEGER
				{
				disable(1) ,
				enable(2)
				}
			MAX-ACCESS read-write
			STATUS current
			DESCRIPTION 
				"This object indicates the status of the IPv6 function of users. The default value is 1 ? 1: disable 2: enable."
			::= { hwWlanGlobalConfig 6 }

		 --1.3.6.1.4.1.2011.6.139.11.1.1.7
		hwWlanApDataCollectionInterval OBJECT-TYPE
			SYNTAX Integer32 (5..60 | 255)
			MAX-ACCESS read-write
			STATUS current
			DESCRIPTION 
				"This object indicates the period of caching AP performance. The default value is 15. It is expressed in minutes."
			::= { hwWlanGlobalConfig 7 }

		 --1.3.6.1.4.1.2011.6.139.11.1.1.8
		hwTestRtCollectOnoff OBJECT-TYPE
			SYNTAX Integer32
			MAX-ACCESS read-write
			STATUS current
			DESCRIPTION 
				"This object indicates the status of the real-time collection switch."
			::= { hwWlanGlobalConfig 8 }

		 --1.3.6.1.4.1.2011.6.139.11.1.1.9
		hwTestApNormalCollectCycle OBJECT-TYPE
			SYNTAX Integer32
			MAX-ACCESS read-write
			STATUS current
			DESCRIPTION 
				"This object indicates the regular period of an AC collecting AP performance data."
			::= { hwWlanGlobalConfig 9 }

		 --1.3.6.1.4.1.2011.6.139.11.1.1.10
		hwTestApRtCollectCycle OBJECT-TYPE
			SYNTAX Integer32
			MAX-ACCESS read-write
			STATUS current
			DESCRIPTION 
				"This object indicates the real-time period of an AC collecting AP performance data."
			::= { hwWlanGlobalConfig 10 }

		 --1.3.6.1.4.1.2011.6.139.11.1.1.11
		hwWlanConfigCommitAll OBJECT-TYPE
			SYNTAX Integer32
			MAX-ACCESS read-write
			STATUS current
			DESCRIPTION 
				"Description."
			::= { hwWlanGlobalConfig 11 }

		--1.3.6.1.4.1.2011.6.139.11.1.1.12
		hwWlanProtect OBJECT IDENTIFIER ::= { hwWlanGlobalConfig 12 }

		 --1.3.6.1.4.1.2011.6.139.11.1.1.12.1
		hwWlanProtectIpAddress OBJECT-TYPE
			SYNTAX IpAddress
			MAX-ACCESS read-write
			STATUS current
			DESCRIPTION 
				"This object indicates the IP address of the standby AC."
			::= { hwWlanProtect 1 }

		 --1.3.6.1.4.1.2011.6.139.11.1.1.12.2
		hwWlanProtectIPv6Address OBJECT-TYPE
			SYNTAX OCTET STRING
			MAX-ACCESS read-write
			STATUS current
			DESCRIPTION 
				"This object indicates setting of the IPv6 address of the standby AC."
			::= { hwWlanProtect 2 }

		 --1.3.6.1.4.1.2011.6.139.11.1.1.12.3
		hwWlanProtectPriority OBJECT-TYPE
			SYNTAX Unsigned32 (0..7)
			MAX-ACCESS read-write
			STATUS current
			DESCRIPTION 
				"This object indicates the AC priority that determines whether the AC can be selected as the active AC. The default value is 0."
			::= { hwWlanProtect 3 }

		 --1.3.6.1.4.1.2011.6.139.11.1.1.12.4
		hwWlanProtectSwitch OBJECT-TYPE
			SYNTAX INTEGER
				{
				enable(1) ,
				disable(2)
				}
			MAX-ACCESS read-write
			STATUS current
			DESCRIPTION 
				"This object indicates the status of the hot backup function. The default value is 2."
			::= { hwWlanProtect 4 }

		 --1.3.6.1.4.1.2011.6.139.11.1.1.12.5
		hwWlanProtectRestoreSwitch OBJECT-TYPE
			SYNTAX INTEGER
				{
				enable(1) ,
				disable(2)
				}
			MAX-ACCESS read-write
			STATUS current
			DESCRIPTION 
				"This object indicates the status of the switchback function. The default value is 1."
			::= { hwWlanProtect 5 }

		 --1.3.6.1.4.1.2011.6.139.11.1.1.12.6
		hwUndoWlanProtectIpAddress OBJECT-TYPE
			SYNTAX Integer32
			MAX-ACCESS read-write
			STATUS current
			DESCRIPTION 
				"This object indicates whether to restore the default setting of the IP address of the standby AC."
			::= { hwWlanProtect 6 }

		 --1.3.6.1.4.1.2011.6.139.11.1.1.12.7
		hwUndoWlanProtectPriority OBJECT-TYPE
			SYNTAX Integer32
			MAX-ACCESS read-write
			STATUS current
			DESCRIPTION 
				"This object indicates whether to restore the default setting of the priority of the standby AC."
			::= { hwWlanProtect 7 }

		--1.3.6.1.4.1.2011.6.139.11.1.1.13
		hwWlanBackupHsbConfig OBJECT IDENTIFIER ::= { hwWlanGlobalConfig 13 }

		 --1.3.6.1.4.1.2011.6.139.11.1.1.13.1
		hwWlanCfgHsbServiceType OBJECT-TYPE
			SYNTAX INTEGER
				{
				disable(1),
				hsbGroup(2),
				hsbService(3)
				}
			MAX-ACCESS read-write
			STATUS current
			DESCRIPTION 
				"This object indicates the HSB type. The default value is 1."
			::= { hwWlanBackupHsbConfig 1 }

		 --1.3.6.1.4.1.2011.6.139.11.1.1.13.2
		hwWlanCfgHsbGroupId OBJECT-TYPE
			SYNTAX Unsigned32
			MAX-ACCESS read-write
			STATUS current
			DESCRIPTION 
				"This object indicates the HSB group ID. If the HSB type is set to Disable, the ID is 0xFFFFFFFF."
			::= { hwWlanBackupHsbConfig 2 }

		 --1.3.6.1.4.1.2011.6.139.11.1.1.13.3
		hwWlanCfgHsbTunnelId OBJECT-TYPE
			SYNTAX Unsigned32
			MAX-ACCESS read-write
			STATUS current
			DESCRIPTION 
				"This object indicates the ID of the HSB channel. If the HSB type is set to Disable, the ID is 0xFFFFFFFF."
			::= { hwWlanBackupHsbConfig 3 }

		--1.3.6.1.4.1.2011.6.139.11.1.1.14
		hwWlanCommitTable OBJECT-TYPE
			SYNTAX SEQUENCE OF HwWlanCommitEntry 
			MAX-ACCESS not-accessible
			STATUS current
			DESCRIPTION 
				"Description."
			::= { hwWlanGlobalConfig 14 }

		--1.3.6.1.4.1.2011.6.139.11.1.1.14.1
		hwWlanCommitEntry OBJECT-TYPE
			SYNTAX HwWlanCommitEntry 
			MAX-ACCESS not-accessible
			STATUS current
			DESCRIPTION 
				"Description."
			INDEX { hwWlanCommitApMac }
			::= { hwWlanCommitTable 1 }


		HwWlanCommitEntry ::=
			SEQUENCE {				
				hwWlanCommitApMac
					MacAddress,
				hwWlanConfigCommit
					Integer32 
			 }

		 --1.3.6.1.4.1.2011.6.139.11.1.1.14.1.1
		hwWlanCommitApMac OBJECT-TYPE
			SYNTAX MacAddress
			MAX-ACCESS not-accessible
			STATUS current
			DESCRIPTION 
				"Description."
			::= { hwWlanCommitEntry 1 }

		 --1.3.6.1.4.1.2011.6.139.11.1.1.14.1.2
		hwWlanConfigCommit OBJECT-TYPE
			SYNTAX Integer32
			MAX-ACCESS read-write
			STATUS current
			DESCRIPTION 
				"Description."
			::= { hwWlanCommitEntry 2 }

		
		-- 1.3.6.1.4.1.2011.6.139.11.1.1.15
		hwWlanReportStaInfo OBJECT-TYPE
			SYNTAX INTEGER
				{
				disable(1),
				enable(2)
				}
			MAX-ACCESS read-write
			STATUS current
			DESCRIPTION
				"Description."
			::= { hwWlanGlobalConfig 15 }

		-- 1.3.6.1.4.1.2011.6.139.11.1.1.16
		hwWlanBLELowPowerWarningThreshold OBJECT-TYPE
			SYNTAX Integer32
			MAX-ACCESS read-write
			STATUS current
			DESCRIPTION
				"Description."
			::= { hwWlanGlobalConfig 16 }

		-- 1.3.6.1.4.1.2011.6.139.11.1.1.17
		hwWlanBLEMonitorListTable OBJECT-TYPE
			SYNTAX SEQUENCE OF HwWlanBLEMonitorListEntry
			MAX-ACCESS not-accessible
			STATUS current
			DESCRIPTION
				"Description."
			::= { hwWlanGlobalConfig 17 }
			
		-- 1.3.6.1.4.1.2011.6.139.11.1.1.17.1
		hwWlanBLEMonitorListEntry OBJECT-TYPE
			SYNTAX HwWlanBLEMonitorListEntry
			MAX-ACCESS not-accessible
			STATUS current
			DESCRIPTION
				"Description."
			INDEX { hwWlanBLEMonitoringListMac }
			::= { hwWlanBLEMonitorListTable 1 }
			
		HwWlanBLEMonitorListEntry ::=
			SEQUENCE { 
				hwWlanBLEMonitoringListMac
					MacAddress,
				hwWlanBLEMonitoringListRowStatue
					RowStatus
			 }

		-- 1.3.6.1.4.1.2011.6.139.11.1.1.17.1.1
		hwWlanBLEMonitoringListMac OBJECT-TYPE
			SYNTAX MacAddress
			MAX-ACCESS not-accessible
			STATUS current
			DESCRIPTION
				"Description."
			::= { hwWlanBLEMonitorListEntry 1 }
			
		-- 1.3.6.1.4.1.2011.6.139.11.1.1.17.1.2
		hwWlanBLEMonitoringListRowStatue OBJECT-TYPE
			SYNTAX RowStatus
			MAX-ACCESS read-write
			STATUS current
			DESCRIPTION
				"Description."
			::= { hwWlanBLEMonitorListEntry 2 }
											
		--1.3.6.1.4.1.2011.6.139.11.1.2
		hwApAuthObjects OBJECT IDENTIFIER ::= { hwWlanConfigObjects 2 }

		 --1.3.6.1.4.1.2011.6.139.11.1.2.1
		hwWlanApAuthMode OBJECT-TYPE
			SYNTAX INTEGER
				{
				macAuth(1) ,
				snAuth(2) ,
				noAuth(3)
				}
			MAX-ACCESS read-write
			STATUS current
			DESCRIPTION 
				"This object indicates the AP authentication mode. The default value is 1."
			::= { hwApAuthObjects 1 }

		--1.3.6.1.4.1.2011.6.139.11.1.2.2
		hwWlanApMacWhitelistTable OBJECT-TYPE
			SYNTAX SEQUENCE OF HwWlanApMacWhitelistEntry 
			MAX-ACCESS not-accessible
			STATUS current
			DESCRIPTION 
				"This table is used to add and delete AP MAC addresses in the white lists."
			::= { hwApAuthObjects 2 }

		--1.3.6.1.4.1.2011.6.139.11.1.2.2.1
		hwWlanApMacWhitelistEntry OBJECT-TYPE
			SYNTAX HwWlanApMacWhitelistEntry 
			MAX-ACCESS not-accessible
			STATUS current
			DESCRIPTION 
				"The index of this table is hwWlanApMacWhitelistMacAddr."
			INDEX { hwWlanApMacWhitelistMacAddr }
			::= { hwWlanApMacWhitelistTable 1 }


		HwWlanApMacWhitelistEntry ::=
			SEQUENCE {				
				hwWlanApMacWhitelistMacAddr
					MacAddress,
				hwWlanApMacWhitelistRowStatus
					RowStatus 
			 }

		 --1.3.6.1.4.1.2011.6.139.11.1.2.2.1.1
		hwWlanApMacWhitelistMacAddr OBJECT-TYPE
			SYNTAX MacAddress
			MAX-ACCESS not-accessible
			STATUS current
			DESCRIPTION 
				"This object indicates the MAC address of an AP."
			::= { hwWlanApMacWhitelistEntry 1 }

		 --1.3.6.1.4.1.2011.6.139.11.1.2.2.1.2
		hwWlanApMacWhitelistRowStatus OBJECT-TYPE
			SYNTAX RowStatus
			MAX-ACCESS read-create
			STATUS current
			DESCRIPTION 
				"This object indicates the row status of this table."
			::= { hwWlanApMacWhitelistEntry 2 }

		--1.3.6.1.4.1.2011.6.139.11.1.2.3
		hwWlanApSnWhitelistTable OBJECT-TYPE
			SYNTAX SEQUENCE OF HwWlanApSnWhitelistEntry 
			MAX-ACCESS not-accessible
			STATUS current
			DESCRIPTION 
				"This table is used to add and delete AP sequence numbers in the white lists of AP sequence numbers."
			::= { hwApAuthObjects 3 }

		--1.3.6.1.4.1.2011.6.139.11.1.2.3.1
		hwWlanApSnWhitelistEntry OBJECT-TYPE
			SYNTAX HwWlanApSnWhitelistEntry 
			MAX-ACCESS not-accessible
			STATUS current
			DESCRIPTION 
				"The index of this table is hwWlanApSnWhitelistSn."
			INDEX { hwWlanApSnWhitelistSn }
			::= { hwWlanApSnWhitelistTable 1 }


		HwWlanApSnWhitelistEntry ::=
			SEQUENCE {				
				hwWlanApSnWhitelistSn
					OCTET STRING,
				hwWlanApSnWhitelistRowStatus
					RowStatus 
			 }

		 --1.3.6.1.4.1.2011.6.139.11.1.2.3.1.1
		hwWlanApSnWhitelistSn OBJECT-TYPE
			SYNTAX OCTET STRING
			MAX-ACCESS not-accessible
			STATUS current
			DESCRIPTION 
				"Description."
			::= { hwWlanApSnWhitelistEntry 1 }

		 --1.3.6.1.4.1.2011.6.139.11.1.2.3.1.2
		hwWlanApSnWhitelistRowStatus OBJECT-TYPE
			SYNTAX RowStatus
			MAX-ACCESS read-create
			STATUS current
			DESCRIPTION 
				"Indicate the row status of this table."
			::= { hwWlanApSnWhitelistEntry 2 }

		--1.3.6.1.4.1.2011.6.139.11.1.2.4
		hwWlanApMacBlacklistTable OBJECT-TYPE
			SYNTAX SEQUENCE OF HwWlanApMacBlacklistEntry 
			MAX-ACCESS not-accessible
			STATUS current
			DESCRIPTION 
				"This table describes the AP MAC blacklist.This table is used to add an AP's MAC address to the blacklist or delete an AP's MAC address from the blacklist."
			::= { hwApAuthObjects 4 }

		--1.3.6.1.4.1.2011.6.139.11.1.2.4.1
		hwWlanApMacBlacklistEntry OBJECT-TYPE
			SYNTAX HwWlanApMacBlacklistEntry 
			MAX-ACCESS not-accessible
			STATUS current
			DESCRIPTION 
				"The index of this table is hwWlanApMacBlacklistMacAddr."
			INDEX { hwWlanApMacBlacklistMacAddr }
			::= { hwWlanApMacBlacklistTable 1 }


		HwWlanApMacBlacklistEntry ::=
			SEQUENCE {				
				hwWlanApMacBlacklistMacAddr
					MacAddress,
				hwWlanApMacBlacklistRowStatus
					RowStatus 
			 }

		 --1.3.6.1.4.1.2011.6.139.11.1.2.4.1.1
		hwWlanApMacBlacklistMacAddr OBJECT-TYPE
			SYNTAX MacAddress
			MAX-ACCESS not-accessible
			STATUS current
			DESCRIPTION 
				"This object indicates the MAC address of an AP."
			::= { hwWlanApMacBlacklistEntry 1 }

		 --1.3.6.1.4.1.2011.6.139.11.1.2.4.1.2
		hwWlanApMacBlacklistRowStatus OBJECT-TYPE
			SYNTAX RowStatus
			MAX-ACCESS read-create
			STATUS current
			DESCRIPTION 
				"This object indicates the row status of this table."
			::= { hwWlanApMacBlacklistEntry 2 }

		--1.3.6.1.4.1.2011.6.139.11.1.3
		hwAPGroupTable OBJECT-TYPE
			SYNTAX SEQUENCE OF HwAPGroupEntry 
			MAX-ACCESS not-accessible
			STATUS current
			DESCRIPTION 
				"This table is used to create or delete AP groups and bind or unbind the AP system profile, 2G radio profile, and domain profile."
			::= { hwWlanConfigObjects 3 }

		--1.3.6.1.4.1.2011.6.139.11.1.3.1
		hwAPGroupEntry OBJECT-TYPE
			SYNTAX HwAPGroupEntry 
			MAX-ACCESS not-accessible
			STATUS current
			DESCRIPTION 
				"The index of this table is hwAPGroupName."
			INDEX { hwAPGroupName }
			::= { hwAPGroupTable 1 }


		HwAPGroupEntry ::=
			SEQUENCE { 
				hwAPGroupName
					OCTET STRING,
				hwAPGrpAPSystemProfile
					OCTET STRING,
				hwAPGrpDomainProfile
					OCTET STRING,
				hwAPGrpRowStatus
					RowStatus,
				hwAPGrpWidsProfile
					OCTET STRING
			 }

		 --1.3.6.1.4.1.2011.6.139.11.1.3.1.1
		hwAPGroupName OBJECT-TYPE
			SYNTAX OCTET STRING (SIZE (1..35))
			MAX-ACCESS not-accessible
			STATUS current
			DESCRIPTION 
				"This object indicates the AP group name. It is the index of the table."
			::= { hwAPGroupEntry 1 }

		 --1.3.6.1.4.1.2011.6.139.11.1.3.1.2
		hwAPGrpAPSystemProfile OBJECT-TYPE
			SYNTAX OCTET STRING (SIZE (1..35))
			MAX-ACCESS read-write
			STATUS current
			DESCRIPTION 
				"This object indicates the system profile to which AP groups are bound. The default value is default."
			::= { hwAPGroupEntry 2 }

		
		-- 1.3.6.1.4.1.2011.6.139.11.1.3.1.4
		hwAPGrpDomainProfile OBJECT-TYPE
			SYNTAX OCTET STRING (SIZE (1..35))
			MAX-ACCESS read-write
			STATUS current
			DESCRIPTION 
				"This object indicates the domain profile to which AP groups are bound. The default value is default."
			::= { hwAPGroupEntry 4 }

		
		-- 1.3.6.1.4.1.2011.6.139.11.1.3.1.5
		hwAPGrpRowStatus OBJECT-TYPE
			SYNTAX RowStatus
			MAX-ACCESS read-write
			STATUS current
			DESCRIPTION 
				"This object indicates the row status of this table. ROWSTATUS_CREATEANDFLOW and ROWSTATUS_DESTROY are commonly used ?	ROWSTATUS_UNDEFINED: undefined  ROWSTATUS_ACTIVE: active ROWSTATUS_NOTINSERVICE: notInService ?	ROWSTATUS_NOTREADY: notReady ?	ROWSTATUS_CREATEANDFLOW: createAndGo ? ROWSTATUS_CREATEANDWAIT: createAndWait ?	ROWSTATUS_DESTROY: destroy"
			::= { hwAPGroupEntry 5 }

		
		-- 1.3.6.1.4.1.2011.6.139.11.1.3.1.6
		hwAPGrpWidsProfile OBJECT-TYPE
			SYNTAX OCTET STRING (SIZE (0..35))
			MAX-ACCESS read-write
			STATUS current
			DESCRIPTION
				"This object indicates the bound WIDS profile."
			::= { hwAPGroupEntry 6 }

		
		-- 1.3.6.1.4.1.2011.6.139.11.1.4
		hwAPGroupWiredPortTable OBJECT-TYPE
			SYNTAX SEQUENCE OF HwAPGroupWiredPortEntry 
			MAX-ACCESS not-accessible
			STATUS current
			DESCRIPTION 
				"This table is the AP wired port profile table.This table is used to bind a wired port profile to an AP group or unbind a wired port profile from an AP group."
			::= { hwWlanConfigObjects 4 }

		--1.3.6.1.4.1.2011.6.139.11.1.4.1
		hwAPGroupWiredPortEntry OBJECT-TYPE
			SYNTAX HwAPGroupWiredPortEntry 
			MAX-ACCESS not-accessible
			STATUS current
			DESCRIPTION 
				"Indexes of this table are hwAPGroupName, hwAPGrpWPInterfaceType, and hwAPGrpWPInterfaceNum."
			INDEX { hwAPGroupName, hwAPGrpWPInterfaceType, hwAPGrpWPInterfaceNum }
			::= { hwAPGroupWiredPortTable 1 }


		HwAPGroupWiredPortEntry ::=
			SEQUENCE {				
				hwAPGrpWPInterfaceType
					INTEGER,
				hwAPGrpWPInterfaceNum
					Unsigned32,
				hwAPGrpWPProfile
					OCTET STRING,
				hwAPGrpWPRowStatus
					RowStatus 
			 }

		 --1.3.6.1.4.1.2011.6.139.11.1.4.1.1
		hwAPGrpWPInterfaceType OBJECT-TYPE
			SYNTAX INTEGER
				{
				fe(1) ,
				ge(2) ,
				trunk(3)
				}
			MAX-ACCESS not-accessible
			STATUS current
			DESCRIPTION 
				"This object indicates the interface type. It is the index of the table."
			::= { hwAPGroupWiredPortEntry 1 }

		 --1.3.6.1.4.1.2011.6.139.11.1.4.1.2
		hwAPGrpWPInterfaceNum OBJECT-TYPE
			SYNTAX Unsigned32 (0..27)
			MAX-ACCESS not-accessible
			STATUS current
			DESCRIPTION 
				"This object indicates the interface index."
			::= { hwAPGroupWiredPortEntry 2 }

		 --1.3.6.1.4.1.2011.6.139.11.1.4.1.3
		hwAPGrpWPProfile OBJECT-TYPE
			SYNTAX OCTET STRING (SIZE (1..35))
			MAX-ACCESS read-write
			STATUS current
			DESCRIPTION 
				"This object indicates the bound wired port profile."
			::= { hwAPGroupWiredPortEntry 3 }

		 --1.3.6.1.4.1.2011.6.139.11.1.4.1.4
		hwAPGrpWPRowStatus OBJECT-TYPE
			SYNTAX RowStatus
			MAX-ACCESS read-write
			STATUS current
			DESCRIPTION 
				"This object indicates the row status of this table. ROWSTATUS_CREATEAN."
			::= { hwAPGroupWiredPortEntry 4 }

		--1.3.6.1.4.1.2011.6.139.11.1.5
		hwAPGroupRadioTable OBJECT-TYPE
			SYNTAX SEQUENCE OF HwAPGroupRadioEntry 
			MAX-ACCESS not-accessible
			STATUS current
			DESCRIPTION 
				"This table is used to bind a 5G radio profile, Mesh profile, WDS profile, WIDS profile, location profile, or spectrum profile to an AP group or unbind a 5G radio profile, Mesh profile, WDS profile, WIDS profile, location profile, or spectrum profile from an AP group.."
			::= { hwWlanConfigObjects 5 }

		--1.3.6.1.4.1.2011.6.139.11.1.5.1
		hwAPGroupRadioEntry OBJECT-TYPE
			SYNTAX HwAPGroupRadioEntry 
			MAX-ACCESS not-accessible
			STATUS current
			DESCRIPTION 
				"Indexes of this table are hwAPGroupName and hwAPGrpRadioId."
			INDEX { hwAPGrpRadioId, hwAPGroupName }
			::= { hwAPGroupRadioTable 1 }


		HwAPGroupRadioEntry ::=
			SEQUENCE {				
				hwAPGrpRadioId
					Unsigned32,
				hwAPGrpRadio5gProfile
					OCTET STRING,
				hwAPGrpMeshProfile
					OCTET STRING,
				hwAPGrpWdsProfile
					OCTET STRING,
				hwAPGrpLocationProfile
					OCTET STRING, 
				hwAPGrpRadioRowStatus
					RowStatus,
				hwAPGrpRadio2gProfile
					OCTET STRING,
				hwAPGrpMeshWhitelistProfile
					OCTET STRING,
				hwAPGrpWdsWhitelistProfile
					OCTET STRING,
				hwAPGrpRadioSwitch
					INTEGER,
				hwAPGrpRadioChannel
					Unsigned32,
				hwAPGrpRadioBandwidth
					INTEGER,
				hwAPGrpRadioEirp
					Unsigned32,
				hwAPGrpRadioAntennaGain
					Unsigned32,
				hwAPGrpRadioCoverageDistance
					Unsigned32,
				hwAPGrpRadioWorkMode
					INTEGER,
				hwAPGrpRadioFrequency
					INTEGER,
				hwAPGrpSpectrumAnalysisSwitch
					INTEGER,
				hwAPGrpWidsDeviceDetectSwitch
					INTEGER,
				hwAPGrpWidsAttackDetectEnBmp
					Unsigned32,
				hwAPGrpWidsRogueContainSwitch
					INTEGER,
				hwAPGrpRadioSecondChannel
					Unsigned32
			 }

		 --1.3.6.1.4.1.2011.6.139.11.1.5.1.1
		hwAPGrpRadioId OBJECT-TYPE
			SYNTAX Unsigned32 (0..2)
			MAX-ACCESS not-accessible
			STATUS current
			DESCRIPTION 
				"This object indicates the radio ID. It is the index of the table."
			::= { hwAPGroupRadioEntry 1 }

		 --1.3.6.1.4.1.2011.6.139.11.1.5.1.2
		hwAPGrpRadio5gProfile OBJECT-TYPE
			SYNTAX OCTET STRING (SIZE (1..35))
			MAX-ACCESS read-write
			STATUS current
			DESCRIPTION 
				"This object indicates the bound 5G radio profile."
			::= { hwAPGroupRadioEntry 2 }

		 --1.3.6.1.4.1.2011.6.139.11.1.5.1.3
		hwAPGrpMeshProfile OBJECT-TYPE
			SYNTAX OCTET STRING (SIZE (0..35))
			MAX-ACCESS read-write
			STATUS current
			DESCRIPTION 
				"This object indicates the bound Mesh profile."
			::= { hwAPGroupRadioEntry 3 }

		 --1.3.6.1.4.1.2011.6.139.11.1.5.1.4
		hwAPGrpWdsProfile OBJECT-TYPE
			SYNTAX OCTET STRING (SIZE (0..35))
			MAX-ACCESS read-write
			STATUS current
			DESCRIPTION 
				"This object indicates the bound WDS profile."
			::= { hwAPGroupRadioEntry 4 }

		--1.3.6.1.4.1.2011.6.139.11.1.5.1.6
		hwAPGrpLocationProfile OBJECT-TYPE
			SYNTAX OCTET STRING (SIZE (0..35))
			MAX-ACCESS read-write
			STATUS current
			DESCRIPTION 
				"This object indicates the bound location profile."
			::= { hwAPGroupRadioEntry 6 } 
		
		-- 1.3.6.1.4.1.2011.6.139.11.1.5.1.8
		hwAPGrpRadioRowStatus OBJECT-TYPE
			SYNTAX RowStatus
			MAX-ACCESS read-write
			STATUS current
			DESCRIPTION 
				"This object indicates the row status of this table. ROWSTATUS_CREATEANDFLOW and ROWSTATUS_DESTROY are commonly used ? ROWSTATUS_UNDEFINED: undefined ?	ROWSTATUS_ACTIVE: active ?	ROWSTATUS_NOTINSERVICE: notInService ?	ROWSTATUS_NOTREADY: notReady ?	ROWSTATUS_CREATEANDFLOW: createAndGo ?	ROWSTATUS_CREATEANDWAIT: createAndWait ? ROWSTATUS_DESTROY: destroy."
			::= { hwAPGroupRadioEntry 8 }


		-- 1.3.6.1.4.1.2011.6.139.11.1.5.1.9
		hwAPGrpRadio2gProfile OBJECT-TYPE
			SYNTAX OCTET STRING (SIZE (1..35))
			MAX-ACCESS read-write
			STATUS current
			DESCRIPTION
				"This object indicates the 2G radio profile to which AP groups are bound. The default value is default."
			::= { hwAPGroupRadioEntry 9 }


		-- 1.3.6.1.4.1.2011.6.139.11.1.5.1.10
		hwAPGrpMeshWhitelistProfile OBJECT-TYPE
			SYNTAX OCTET STRING (SIZE (0..35))
			MAX-ACCESS read-write
			STATUS current
			DESCRIPTION
				"This object indicates the bound whitelist profile."
			::= { hwAPGroupRadioEntry 10 }

		
		-- 1.3.6.1.4.1.2011.6.139.11.1.5.1.11
		hwAPGrpWdsWhitelistProfile OBJECT-TYPE
			SYNTAX OCTET STRING (SIZE (0..35))
			MAX-ACCESS read-write
			STATUS current
			DESCRIPTION
				"This object indicates the bound whitelist profile."
			::= { hwAPGroupRadioEntry 11 }

		
		-- 1.3.6.1.4.1.2011.6.139.11.1.5.1.12
		hwAPGrpRadioSwitch OBJECT-TYPE
			SYNTAX INTEGER
				{
				disable(1),
				enable(2)
				}
			MAX-ACCESS read-write
			STATUS current
			DESCRIPTION
				"This object indicates the name of a 2G radio profile. It is the index of the table."
			::= { hwAPGroupRadioEntry 12 }

		
		-- 1.3.6.1.4.1.2011.6.139.11.1.5.1.13
		hwAPGrpRadioChannel OBJECT-TYPE
			SYNTAX Unsigned32
			MAX-ACCESS read-write
			STATUS current
			DESCRIPTION
				"This object indicates a radio-frequency channel. For 2.4G, the value ranges from 1 to 13. For 5G, the value ranges from 36 to 165 (with a separation interval of 4)."
			::= { hwAPGroupRadioEntry 13 }

		
		-- 1.3.6.1.4.1.2011.6.139.11.1.5.1.14
		hwAPGrpRadioBandwidth OBJECT-TYPE
			SYNTAX INTEGER
				{
				ht20(1),
				ht40Plus(2),
				ht40Minus(3),
				ht80(4),
				ht160(5),
				invalid(255) 
				}
			MAX-ACCESS read-write
			STATUS current
			DESCRIPTION
				"This object indicate a bandwidth. The default value is 1."
			::= { hwAPGroupRadioEntry 14 }


		-- 1.3.6.1.4.1.2011.6.139.11.1.5.1.15
		hwAPGrpRadioEirp OBJECT-TYPE
			SYNTAX Unsigned32 (1..127)
			MAX-ACCESS read-write
			STATUS current
			DESCRIPTION
				"This object indicates a power value. The default value is 127. The configuration is saved but the actual power is determined by the maximum power supported by the AP."
			::= { hwAPGroupRadioEntry 15 }


		-- 1.3.6.1.4.1.2011.6.139.11.1.5.1.16
		hwAPGrpRadioAntennaGain OBJECT-TYPE
			SYNTAX Unsigned32 (0..30 | 255)
			MAX-ACCESS read-write
			STATUS current
			DESCRIPTION
				"This object indicates antenna gains. The default value 0xFF indicates that the default gain of an AP is used. It is expressed in dB. Default gains vary with different types of APs."
			::= { hwAPGroupRadioEntry 16 }


		-- 1.3.6.1.4.1.2011.6.139.11.1.5.1.17
		hwAPGrpRadioCoverageDistance OBJECT-TYPE
			SYNTAX Unsigned32 (1..400)
			MAX-ACCESS read-write
			STATUS current
			DESCRIPTION
				"This object indicates a radio coverage distance. The default value is 3. The unit is 0.1 km."
			::= { hwAPGroupRadioEntry 17 }


		-- 1.3.6.1.4.1.2011.6.139.11.1.5.1.18
		hwAPGrpRadioWorkMode OBJECT-TYPE
			SYNTAX INTEGER
				{
				normal(1),
				monitor(2),
				dualband(3)
				}
			MAX-ACCESS read-write
			STATUS current
			DESCRIPTION
				"This object indicates the radio working mode. The default value is 1."
			::= { hwAPGroupRadioEntry 18 }


		-- 1.3.6.1.4.1.2011.6.139.11.1.5.1.19
		hwAPGrpRadioFrequency OBJECT-TYPE
			SYNTAX INTEGER
				{
				frequency2G(1),
				frequency5G(2)
				}
			MAX-ACCESS read-write
			STATUS current
			DESCRIPTION
				"This object indicates the setting of the frequency band for radio 0. The default value is 1. 1: frequency2G, 2: frequency5G."
			::= { hwAPGroupRadioEntry 19 }

		

		-- 1.3.6.1.4.1.2011.6.139.11.1.5.1.20
		hwAPGrpSpectrumAnalysisSwitch OBJECT-TYPE
			SYNTAX INTEGER
				{
				disable(1),
				enable(2)
				}
			MAX-ACCESS read-write
			STATUS current
			DESCRIPTION
				"This object indicates the status of the spectrum analysis function. The default value is 1."
			::= { hwAPGroupRadioEntry 20 }

		

		-- 1.3.6.1.4.1.2011.6.139.11.1.5.1.21
		hwAPGrpWidsDeviceDetectSwitch OBJECT-TYPE
			SYNTAX INTEGER
				{
				disable(1),
				enable(2)
				}
			MAX-ACCESS read-write
			STATUS current
			DESCRIPTION
				"This object indicates the status of the device detection function. The default value is 1."
			::= { hwAPGroupRadioEntry 21 }

		

		-- 1.3.6.1.4.1.2011.6.139.11.1.5.1.22
		hwAPGrpWidsAttackDetectEnBmp OBJECT-TYPE
			SYNTAX Unsigned32
			MAX-ACCESS read-write
			STATUS current
			DESCRIPTION
				"This object indicates the bit map of the brute force attack switch. bit0:weak-iv, bit1:spoof, bit2:flood, bit3:wpa-psk, bit4:wpa2-psk, bit5:wapi-psk, bit6:wep-psk."
			::= { hwAPGroupRadioEntry 22 }

		

		-- 1.3.6.1.4.1.2011.6.139.11.1.5.1.23
		hwAPGrpWidsRogueContainSwitch OBJECT-TYPE
			SYNTAX INTEGER
				{
				disable(1),
				enable(2)
				}
			MAX-ACCESS read-write
			STATUS current
			DESCRIPTION
				"This object indicates the status of the device detection function. The default value is 1."
			::= { hwAPGroupRadioEntry 23 }

		-- 1.3.6.1.4.1.2011.6.139.11.1.5.1.24
		hwAPGrpRadioSecondChannel OBJECT-TYPE
			SYNTAX Unsigned32
			MAX-ACCESS read-write
			STATUS current
			DESCRIPTION
				"This object indicates a radio-frequency channel. For 2.4G, the value ranges from 1 to 13. For 5G, the value ranges from 36 to 165 (with a separation interval of 4)."
			::= { hwAPGroupRadioEntry 24 }		

		-- 1.3.6.1.4.1.2011.6.139.11.1.6
		hwAPGroupVapTable OBJECT-TYPE
			SYNTAX SEQUENCE OF HwAPGroupVapEntry 
			MAX-ACCESS not-accessible
			STATUS current
			DESCRIPTION 
				"This table is used to create VAPs in an AP group."
			::= { hwWlanConfigObjects 6 }

		--1.3.6.1.4.1.2011.6.139.11.1.6.1
		hwAPGroupVapEntry OBJECT-TYPE
			SYNTAX HwAPGroupVapEntry 
			MAX-ACCESS not-accessible
			STATUS current
			DESCRIPTION 
				"Indexes of this table are hwAPGroupName, hwAPGrpRadioId, and hwAPGrpWlanId."
			INDEX { hwAPGroupName, hwAPGrpRadioId, hwAPGrpWlanId }
			::= { hwAPGroupVapTable 1 }


		HwAPGroupVapEntry ::=
			SEQUENCE {				
				hwAPGrpWlanId
					Unsigned32,
				hwAPGrpVapProfile
					OCTET STRING,
				hwAPGrpVapRowStatus
					RowStatus 
			 }

		 --1.3.6.1.4.1.2011.6.139.11.1.6.1.1
		hwAPGrpWlanId OBJECT-TYPE
			SYNTAX Unsigned32 (1..16)
			MAX-ACCESS not-accessible
			STATUS current
			DESCRIPTION 
				"This object indicates the WLAN ID. It is the index of the table."
			::= { hwAPGroupVapEntry 1 }

		 --1.3.6.1.4.1.2011.6.139.11.1.6.1.2
		hwAPGrpVapProfile OBJECT-TYPE
			SYNTAX OCTET STRING (SIZE (1..35))
			MAX-ACCESS read-write
			STATUS current
			DESCRIPTION 
				"This object indicates the bound VAP profile."
			::= { hwAPGroupVapEntry 2 }

		 --1.3.6.1.4.1.2011.6.139.11.1.6.1.3
		hwAPGrpVapRowStatus OBJECT-TYPE
			SYNTAX RowStatus
			MAX-ACCESS read-write
			STATUS current
			DESCRIPTION 
				"This object indicates the row status of this table. ROWSTATUS_CREATEANDFLOW and ROWSTATUS_DESTROY are commonly used."
			::= { hwAPGroupVapEntry 3 }

		--1.3.6.1.4.1.2011.6.139.11.1.7
		hwAPSpecificTable OBJECT-TYPE
			SYNTAX SEQUENCE OF HwAPSpecificEntry 
			MAX-ACCESS not-accessible
			STATUS current
			DESCRIPTION 
				"This table is used to create or delete an AP specific profile and bind an AP system profile, 2G radio profile, or domain profile to it or unbind an AP system profile, 2G radio profile, or domain profile from it."
			::= { hwWlanConfigObjects 7 }

		--1.3.6.1.4.1.2011.6.139.11.1.7.1
		hwAPSpecificEntry OBJECT-TYPE
			SYNTAX HwAPSpecificEntry 
			MAX-ACCESS not-accessible
			STATUS current
			DESCRIPTION 
				"The index of this table is hwAPSpApMac."
			INDEX { hwAPSpApMac }
			::= { hwAPSpecificTable 1 }


		HwAPSpecificEntry ::=
			SEQUENCE { 
				hwAPSpAPSystemProfile
					OCTET STRING,
				hwAPSpDomainProfile
					OCTET STRING,
				hwAPSpRowStatus
					RowStatus,
				hwAPSpApMac
					MacAddress,
				hwAPSpApId
					Unsigned32,
				hwAPSpApTypeInfo
					OCTET STRING,
				hwAPSpWidsProfile
					OCTET STRING
			 }

		-- 1.3.6.1.4.1.2011.6.139.11.1.7.1.2
		hwAPSpAPSystemProfile OBJECT-TYPE
			SYNTAX OCTET STRING (SIZE (0..35))
			MAX-ACCESS read-write
			STATUS current
			DESCRIPTION 
				"This object indicates the system profile bound to the AP specific profile."
			::= { hwAPSpecificEntry 2 }


		-- 1.3.6.1.4.1.2011.6.139.11.1.7.1.4
		hwAPSpDomainProfile OBJECT-TYPE
			SYNTAX OCTET STRING (SIZE (0..35))
			MAX-ACCESS read-write
			STATUS current
			DESCRIPTION 
				"This object indicates the domain profile bound to the AP specific profile."
			::= { hwAPSpecificEntry 4 }


		-- 1.3.6.1.4.1.2011.6.139.11.1.7.1.5
		hwAPSpRowStatus OBJECT-TYPE
			SYNTAX RowStatus
			MAX-ACCESS read-write
			STATUS current
			DESCRIPTION 
				"This object indicates the row status of this table. ROWSTATUS_CREATEANDFLOW and ROWSTATUS_DESTROY are commonly used?	ROWSTATUS_UNDEFINED: undefined ?	ROWSTATUS_ACTIVE: active ?	ROWSTATUS_NOTINSERVICE: notInService ?	ROWSTATUS_NOTREADY: notReady ?	ROWSTATUS_CREATEANDFLOW: createAndGo ?	ROWSTATUS_CREATEANDWAIT: createAndWait ?	ROWSTATUS_DESTROY: destroy."
			::= { hwAPSpecificEntry 5 }


		-- 1.3.6.1.4.1.2011.6.139.11.1.7.1.6
		hwAPSpApMac OBJECT-TYPE
			SYNTAX MacAddress
			MAX-ACCESS not-accessible
			STATUS current
			DESCRIPTION
				"This object indicates the MAC address of an AP."
			::= { hwAPSpecificEntry 6 }


		-- 1.3.6.1.4.1.2011.6.139.11.1.7.1.7
		hwAPSpApId OBJECT-TYPE
			SYNTAX Unsigned32
			MAX-ACCESS read-write
			STATUS current
			DESCRIPTION
				"This object indicates the AP ID."
			::= { hwAPSpecificEntry 7 }


		-- 1.3.6.1.4.1.2011.6.139.11.1.7.1.8
		hwAPSpApTypeInfo OBJECT-TYPE
			SYNTAX OCTET STRING (SIZE (0..35))
			MAX-ACCESS read-write
			STATUS current
			DESCRIPTION
				"This object indicates the domain profile bound to the AP specific profile."
			::= { hwAPSpecificEntry 8 }


		-- 1.3.6.1.4.1.2011.6.139.11.1.7.1.9
		hwAPSpWidsProfile OBJECT-TYPE
			SYNTAX OCTET STRING (SIZE (0..35))
			MAX-ACCESS read-write
			STATUS current
			DESCRIPTION
				"This object indicates the bound WIDS profile."
			::= { hwAPSpecificEntry 9 }


		-- 1.3.6.1.4.1.2011.6.139.11.1.8
		hwAPSpecificWiredPortTable OBJECT-TYPE
			SYNTAX SEQUENCE OF HwAPSpecificWiredPortEntry 
			MAX-ACCESS not-accessible
			STATUS current
			DESCRIPTION 
				"This table is used to bind an AP wired port profile to an AP specific profile or unbind an AP wired port profile from an AP specific profile.."
			::= { hwWlanConfigObjects 8 }

		--1.3.6.1.4.1.2011.6.139.11.1.8.1
		hwAPSpecificWiredPortEntry OBJECT-TYPE
			SYNTAX HwAPSpecificWiredPortEntry 
			MAX-ACCESS not-accessible
			STATUS current
			DESCRIPTION 
				"Indexes of this table are  hwAPSpWPInterfaceType, hwAPSpWPInterfaceNum and hwAPSpApMac."
			INDEX { hwAPSpWPInterfaceType, hwAPSpWPInterfaceNum, hwAPSpApMac }
			::= { hwAPSpecificWiredPortTable 1 }


		HwAPSpecificWiredPortEntry ::=
			SEQUENCE {				
				hwAPSpWPInterfaceType
					INTEGER,
				hwAPSpWPInterfaceNum
					Unsigned32,
				hwAPSpWPProfile
					OCTET STRING,
				hwAPSpWPRowStatus
					RowStatus,
				hwAPSpWPApId
					Unsigned32
			 }

		 --1.3.6.1.4.1.2011.6.139.11.1.8.1.1
		hwAPSpWPInterfaceType OBJECT-TYPE
			SYNTAX INTEGER
				{
				fe(1),
				ge(2) ,
				trunk(3)
				}
			MAX-ACCESS not-accessible
			STATUS current
			DESCRIPTION 
				"This object indicates the interface type."
			::= { hwAPSpecificWiredPortEntry 1 }

		 --1.3.6.1.4.1.2011.6.139.11.1.8.1.2
		hwAPSpWPInterfaceNum OBJECT-TYPE
			SYNTAX Unsigned32 (0..27)
			MAX-ACCESS not-accessible
			STATUS current
			DESCRIPTION 
				"This object indicates the interface index."
			::= { hwAPSpecificWiredPortEntry 2 }

		 --1.3.6.1.4.1.2011.6.139.11.1.8.1.3
		hwAPSpWPProfile OBJECT-TYPE
			SYNTAX OCTET STRING (SIZE (0..35))
			MAX-ACCESS read-write
			STATUS current
			DESCRIPTION 
				"This object indicates the bound wired port profile."
			::= { hwAPSpecificWiredPortEntry 3 }

		 --1.3.6.1.4.1.2011.6.139.11.1.8.1.4
		hwAPSpWPRowStatus OBJECT-TYPE
			SYNTAX RowStatus
			MAX-ACCESS read-write
			STATUS current
			DESCRIPTION 
				"This object indicates the row status of this table. ROWSTATUS_CREATEANDFLOW and ROWSTATUS_DESTROY are commonly used?	ROWSTATUS_UNDEFINED: undefined ?	ROWSTATUS_ACTIVE: active ?	ROWSTATUS_NOTINSERVICE: notInService ?	ROWSTATUS_NOTREADY: notReady ?	ROWSTATUS_CREATEANDFLOW: createAndGo ?	ROWSTATUS_CREATEANDWAIT: createAndWait ?	ROWSTATUS_DESTROY: destroy."
			::= { hwAPSpecificWiredPortEntry 4 }

		-- 1.3.6.1.4.1.2011.6.139.11.1.8.1.5
		hwAPSpWPApId OBJECT-TYPE
			SYNTAX Unsigned32
			MAX-ACCESS read-only
			STATUS current
			DESCRIPTION
				"This object indicates the AP ID."
			::= { hwAPSpecificWiredPortEntry 5 }

		
		--1.3.6.1.4.1.2011.6.139.11.1.9
		hwAPSpecificRadioTable OBJECT-TYPE
			SYNTAX SEQUENCE OF HwAPSpecificRadioEntry 
			MAX-ACCESS not-accessible
			STATUS current
			DESCRIPTION 
				"This table records the information about profiles bound based on radio in an AP specific profile, including 5G radio profile, Mesh profile, WDS profile, WIDS profile, location profile, and spectrum profile."
			::= { hwWlanConfigObjects 9 }

		--1.3.6.1.4.1.2011.6.139.11.1.9.1
		hwAPSpecificRadioEntry OBJECT-TYPE
			SYNTAX HwAPSpecificRadioEntry 
			MAX-ACCESS not-accessible
			STATUS current
			DESCRIPTION 
				"Indexes of this table are hwAPSpecificName and hwAPSpRadio."
			INDEX { hwAPSpRadio,hwAPSpApMac }
			::= { hwAPSpecificRadioTable 1 }


		HwAPSpecificRadioEntry ::=
			SEQUENCE {				
				hwAPSpRadio
					Unsigned32,
				hwAPSp5gRadioProfile
					OCTET STRING,
				hwAPSpMeshProfile
					OCTET STRING,
				hwAPSpWdsProfile
					OCTET STRING,
				hwAPSpLocationProfile
					OCTET STRING,
				hwAPSpRadioRowStatus
					RowStatus,
				hwAPSpRadio2gProfile
					OCTET STRING,
				hwAPSpMeshWhitelistProfile
					OCTET STRING,
				hwAPSpWdsWhitelistProfile
					OCTET STRING,
				hwAPSpRadioSwitch
					INTEGER,
				hwAPSpRadioChannel
					Unsigned32,
				hwAPSpRadioBandwidth
					INTEGER,
				hwAPSpRadioEirp
					Unsigned32,
				hwAPSpRadioAntennaGain
					Unsigned32,
				hwAPSpRadioCoverageDistance
					Unsigned32,
				hwAPSpRadioWorkMode
					INTEGER,
				hwAPSpRadioFrequency
					INTEGER,
				hwAPSpSpectrumAnalysisSwitch
					INTEGER,
				hwAPSpWidsDeviceDetectSwitch
					INTEGER,
				hwAPSpWidsAttackDetectEnBmp
					Unsigned32,
				hwAPSpWidsRogueContainSwitch
					INTEGER,
				hwAPSpRadioApId
					Unsigned32,
				hwAPSpRadioSecondChannel
					Unsigned32
			 }

		 --1.3.6.1.4.1.2011.6.139.11.1.9.1.1
		hwAPSpRadio OBJECT-TYPE
			SYNTAX Unsigned32 (0..2)
			MAX-ACCESS not-accessible
			STATUS current
			DESCRIPTION 
				"This object indicates the radio ID. It is the index of the table."
			::= { hwAPSpecificRadioEntry 1 }

		 --1.3.6.1.4.1.2011.6.139.11.1.9.1.2
		hwAPSp5gRadioProfile OBJECT-TYPE
			SYNTAX OCTET STRING (SIZE (0..35))
			MAX-ACCESS read-write
			STATUS current
			DESCRIPTION 
				"This object indicates the bound 5G radio profile."
			::= { hwAPSpecificRadioEntry 2 }

		 --1.3.6.1.4.1.2011.6.139.11.1.9.1.3
		hwAPSpMeshProfile OBJECT-TYPE
			SYNTAX OCTET STRING (SIZE (0..35))
			MAX-ACCESS read-write
			STATUS current
			DESCRIPTION 
				"This object indicates the bound Mesh profile."
			::= { hwAPSpecificRadioEntry 3 }

		 --1.3.6.1.4.1.2011.6.139.11.1.9.1.4
		hwAPSpWdsProfile OBJECT-TYPE
			SYNTAX OCTET STRING (SIZE (0..35))
			MAX-ACCESS read-write
			STATUS current
			DESCRIPTION 
				"This object indicates the bound WDS profile."
			::= { hwAPSpecificRadioEntry 4 }

	
	 --1.3.6.1.4.1.2011.6.139.11.1.9.1.6
		hwAPSpLocationProfile OBJECT-TYPE
			SYNTAX OCTET STRING (SIZE (0..35))
			MAX-ACCESS read-write
			STATUS current
			DESCRIPTION 
				"This object indicates the bound location profile."
			::= { hwAPSpecificRadioEntry 6 }
			

		-- 1.3.6.1.4.1.2011.6.139.11.1.9.1.8
		hwAPSpRadioRowStatus OBJECT-TYPE
			SYNTAX RowStatus
			MAX-ACCESS read-write
			STATUS current
			DESCRIPTION 
				"This object indicates the row status of this table. ROWSTATUS_CREATEANDFLOW and ROWSTATUS_DESTROY are commonly used."
			::= { hwAPSpecificRadioEntry 8 }


		-- 1.3.6.1.4.1.2011.6.139.11.1.9.1.9
		hwAPSpRadio2gProfile OBJECT-TYPE
			SYNTAX OCTET STRING (SIZE (0..35))
			MAX-ACCESS read-write
			STATUS current
			DESCRIPTION
				"This object indicates the system profile to which AP groups are bound. The default value is default."
			::= { hwAPSpecificRadioEntry 9 }


		-- 1.3.6.1.4.1.2011.6.139.11.1.9.1.10
		hwAPSpMeshWhitelistProfile OBJECT-TYPE
			SYNTAX OCTET STRING (SIZE (0..35))
			MAX-ACCESS read-write
			STATUS current
			DESCRIPTION
				"This object indicates the bound whitelist profile."
			::= { hwAPSpecificRadioEntry 10 }


		-- 1.3.6.1.4.1.2011.6.139.11.1.9.1.11
		hwAPSpWdsWhitelistProfile OBJECT-TYPE
			SYNTAX OCTET STRING (SIZE (0..35))
			MAX-ACCESS read-write
			STATUS current
			DESCRIPTION
				"This object indicates the bound whitelist profile."
			::= { hwAPSpecificRadioEntry 11 }


		-- 1.3.6.1.4.1.2011.6.139.11.1.9.1.12
		hwAPSpRadioSwitch OBJECT-TYPE
			SYNTAX INTEGER
				{
				disable(1),
				invalid(255)
				}
			MAX-ACCESS read-write
			STATUS current
			DESCRIPTION
				"This object indicates the name of a 2G radio profile. It is the index of the table."
			::= { hwAPSpecificRadioEntry 12 }


		-- 1.3.6.1.4.1.2011.6.139.11.1.9.1.13
		hwAPSpRadioChannel OBJECT-TYPE
			SYNTAX Unsigned32
			MAX-ACCESS read-write
			STATUS current
			DESCRIPTION
				"This object indicates a radio-frequency channel. For 2.4G, the value ranges from 1 to 13. For 5G, the value ranges from 36 to 165 (with a separation interval of 4)."
			::= { hwAPSpecificRadioEntry 13 }


		-- 1.3.6.1.4.1.2011.6.139.11.1.9.1.14
		hwAPSpRadioBandwidth OBJECT-TYPE
			SYNTAX INTEGER
				{
				ht20(1),
				ht40Plus(2),
				ht40Minus(3),
				ht80(4),
				ht160(5),
				invalid(255)
				}
			MAX-ACCESS read-write
			STATUS current
			DESCRIPTION
				"This object indicate a bandwidth. The default value is 1."
			::= { hwAPSpecificRadioEntry 14 }


		-- 1.3.6.1.4.1.2011.6.139.11.1.9.1.15
		hwAPSpRadioEirp OBJECT-TYPE
			SYNTAX Unsigned32 (1..127 | 255)
			MAX-ACCESS read-write
			STATUS current
			DESCRIPTION
				"This object indicates a power value. The default value is 127. The configuration is saved but the actual power is determined by the maximum power supported by the AP."
			::= { hwAPSpecificRadioEntry 15 }


		-- 1.3.6.1.4.1.2011.6.139.11.1.9.1.16
		hwAPSpRadioAntennaGain OBJECT-TYPE
			SYNTAX Unsigned32 (0..30 | 255)
			MAX-ACCESS read-write
			STATUS current
			DESCRIPTION
				"This object indicates antenna gains. The default value 0xFF indicates that the default gain of an AP is used. It is expressed in dB. Default gains vary with different types of APs."
			::= { hwAPSpecificRadioEntry 16 }


		-- 1.3.6.1.4.1.2011.6.139.11.1.9.1.17
		hwAPSpRadioCoverageDistance OBJECT-TYPE
			SYNTAX Unsigned32 (1..400 | 65535)
			MAX-ACCESS read-write
			STATUS current
			DESCRIPTION
				"This object indicates a radio coverage distance. The default value is 3. The unit is 0.1 km."
			::= { hwAPSpecificRadioEntry 17 }


		-- 1.3.6.1.4.1.2011.6.139.11.1.9.1.18
		hwAPSpRadioWorkMode OBJECT-TYPE
			SYNTAX INTEGER
				{
				normal(1),
				monitor(2),
				dualband(3),
				invalid(255)
				}
			MAX-ACCESS read-write
			STATUS current
			DESCRIPTION
				"This object indicates the radio working mode. The default value is 1."
			::= { hwAPSpecificRadioEntry 18 }


		-- 1.3.6.1.4.1.2011.6.139.11.1.9.1.19
		hwAPSpRadioFrequency OBJECT-TYPE
			SYNTAX INTEGER
				{
				frequency2G(1),
				frequency5G(2),
				invalid(255)
				}
			MAX-ACCESS read-write
			STATUS current
			DESCRIPTION
				"This object indicates the setting of the frequency band for radio 0. The default value is invalid. 1: frequency2G, 2: frequency5G."
			::= { hwAPSpecificRadioEntry 19 }

		

		-- 1.3.6.1.4.1.2011.6.139.11.1.9.1.20
		hwAPSpSpectrumAnalysisSwitch OBJECT-TYPE
			SYNTAX INTEGER
				{
				enable(2),
				invalid(255)
				}
			MAX-ACCESS read-write
			STATUS current
			DESCRIPTION
				"This object indicates the status of the spectrum analysis function. The default value is 1."
			::= { hwAPSpecificRadioEntry 20 }

		

		-- 1.3.6.1.4.1.2011.6.139.11.1.9.1.21
		hwAPSpWidsDeviceDetectSwitch OBJECT-TYPE
			SYNTAX INTEGER
				{
				enable(2),
				invalid(255)
				}
			MAX-ACCESS read-write
			STATUS current
			DESCRIPTION
				"This object indicates the status of the device detection function. The default value is 1."
			::= { hwAPSpecificRadioEntry 21 }

		

		-- 1.3.6.1.4.1.2011.6.139.11.1.9.1.22
		hwAPSpWidsAttackDetectEnBmp OBJECT-TYPE
			SYNTAX Unsigned32
			MAX-ACCESS read-write
			STATUS current
			DESCRIPTION
				"This object indicates the bit map of the brute force attack switch. bit0:weak-iv, bit1:spoof, bit2:flood, bit3:wpa-psk, bit4:wpa2-psk, bit5:wapi-psk, bit6:wep-psk."
			::= { hwAPSpecificRadioEntry 22 }

		
		-- 1.3.6.1.4.1.2011.6.139.11.1.9.1.23
		hwAPSpWidsRogueContainSwitch OBJECT-TYPE
			SYNTAX INTEGER
				{
				enable(2),
				invalid(255)
				}
			MAX-ACCESS read-write
			STATUS current
			DESCRIPTION
				"This object indicates the status of the device detection function. The default value is 1."
			::= { hwAPSpecificRadioEntry 23 }


		-- 1.3.6.1.4.1.2011.6.139.11.1.9.1.24
		hwAPSpRadioApId OBJECT-TYPE
			SYNTAX Unsigned32
			MAX-ACCESS read-only
			STATUS current
			DESCRIPTION
				"This object indicates the AP ID."
			::= { hwAPSpecificRadioEntry 24 }

		-- 1.3.6.1.4.1.2011.6.139.11.1.9.1.25
		hwAPSpRadioSecondChannel OBJECT-TYPE
			SYNTAX Unsigned32
			MAX-ACCESS read-write
			STATUS current
			DESCRIPTION
				"This object indicates a radio-frequency channel. For 2.4G, the value ranges from 1 to 13. For 5G, the value ranges from 36 to 165 (with a separation interval of 4)."
			::= { hwAPSpecificRadioEntry 25 }
		
		-- 1.3.6.1.4.1.2011.6.139.11.1.10
		hwAPSpecificVapTable OBJECT-TYPE
			SYNTAX SEQUENCE OF HwAPSpecificVapEntry 
			MAX-ACCESS not-accessible
			STATUS current
			DESCRIPTION 
				"This table is used to create VAPs in an AP specific profile."
			::= { hwWlanConfigObjects 10 }

		--1.3.6.1.4.1.2011.6.139.11.1.10.1
		hwAPSpecificVapEntry OBJECT-TYPE
			SYNTAX HwAPSpecificVapEntry 
			MAX-ACCESS not-accessible
			STATUS current
			DESCRIPTION 
				"Indexes of this table are hwAPSpWlan, hwAPSpRadio, and hwAPSpApMac."
			INDEX { hwAPSpWlan, hwAPSpRadio, hwAPSpApMac}
			::= { hwAPSpecificVapTable 1 }


		HwAPSpecificVapEntry ::=
			SEQUENCE {				
				hwAPSpWlan
					Unsigned32,
				hwAPSpVapProfile
					OCTET STRING,
				hwAPSpVapRowStatus
					RowStatus,
				hwAPSpVapApId
					Unsigned32
			 }

		 --1.3.6.1.4.1.2011.6.139.11.1.10.1.1
		hwAPSpWlan OBJECT-TYPE
			SYNTAX Unsigned32 (1..16)
			MAX-ACCESS not-accessible
			STATUS current
			DESCRIPTION 
				"This object indicates the WLAN ID. It is the index of the table."
			::= { hwAPSpecificVapEntry 1 }

		 --1.3.6.1.4.1.2011.6.139.11.1.10.1.2
		hwAPSpVapProfile OBJECT-TYPE
			SYNTAX OCTET STRING (SIZE (1..35))
			MAX-ACCESS read-write
			STATUS current
			DESCRIPTION 
				"This object indicates the bound VAP profile."
			::= { hwAPSpecificVapEntry 2 }

		 --1.3.6.1.4.1.2011.6.139.11.1.10.1.3
		hwAPSpVapRowStatus OBJECT-TYPE
			SYNTAX RowStatus
			MAX-ACCESS read-write
			STATUS current
			DESCRIPTION 
				"This object indicates the row status of this table. createAndGo(4) and destroy(6) are commonly used."
			::= { hwAPSpecificVapEntry 3 }

		-- 1.3.6.1.4.1.2011.6.139.11.1.10.1.4
		hwAPSpVapApId OBJECT-TYPE
			SYNTAX Unsigned32
			MAX-ACCESS read-only
			STATUS current
			DESCRIPTION
				"This object indicates the AP ID."
			::= { hwAPSpecificVapEntry 4 }

		
		--1.3.6.1.4.1.2011.6.139.11.1.11
		hwRegulatoryDomainProfileTable OBJECT-TYPE
			SYNTAX SEQUENCE OF HwRegulatoryDomainProfileEntry 
			MAX-ACCESS not-accessible
			STATUS current
			DESCRIPTION 
				"This table is used to configure country codes, calibration channels, and calibration channel bandwidths."
			::= { hwWlanConfigObjects 11 }

		--1.3.6.1.4.1.2011.6.139.11.1.11.1
		hwRegulatoryDomainProfileEntry OBJECT-TYPE
			SYNTAX HwRegulatoryDomainProfileEntry 
			MAX-ACCESS not-accessible
			STATUS current
			DESCRIPTION 
				"The index of this table is hwRegulatoryDomainProfileName."
			INDEX { hwRegulatoryDomainProfileName }
			::= { hwRegulatoryDomainProfileTable 1 }


		HwRegulatoryDomainProfileEntry ::=
			SEQUENCE {				
				hwRegulatoryDomainProfileName
					OCTET STRING,
				hwCountryCode
					OCTET STRING,
				hwDcaChannel5GBandwidth
					INTEGER,
				hwDcaChannel5GChannelSet
					OCTET STRING,
				hwDcaChannel2GChannelSet
					OCTET STRING,
				hwRegulatoryDomainProfilRowStatus
					RowStatus 
			 }

		 --1.3.6.1.4.1.2011.6.139.11.1.11.1.1
		hwRegulatoryDomainProfileName OBJECT-TYPE
			SYNTAX OCTET STRING (SIZE (1..35))
			MAX-ACCESS not-accessible
			STATUS current
			DESCRIPTION 
				"This object indicates the name of a regulatory domain profile. It is the index of the table."
			::= { hwRegulatoryDomainProfileEntry 1 }

		 --1.3.6.1.4.1.2011.6.139.11.1.11.1.2
		hwCountryCode OBJECT-TYPE
			SYNTAX OCTET STRING (SIZE (2..8))
			MAX-ACCESS read-write
			STATUS current
			DESCRIPTION 
				"This object indicates the country code. Its value range is subject to the country code table. The default value is CN."
			::= { hwRegulatoryDomainProfileEntry 2 }

		 --1.3.6.1.4.1.2011.6.139.11.1.11.1.3
		hwDcaChannel5GBandwidth OBJECT-TYPE
			SYNTAX INTEGER
				{
				bw20Mhz(1),
				bw40Mhz(2),
				bw80Mhz(3)
				}
			MAX-ACCESS read-write
			STATUS current
			DESCRIPTION 
				"This object indicates the calibration bandwidth on the 5 GHz frequency band. The default value is 1 ?	1: bw20 MHz ?	2: bw40 MHz ?	3: bw80 MHz."
			::= { hwRegulatoryDomainProfileEntry 3 }

		 --1.3.6.1.4.1.2011.6.139.11.1.11.1.4
		hwDcaChannel5GChannelSet OBJECT-TYPE
			SYNTAX OCTET STRING (SIZE (1..256))
			MAX-ACCESS read-write
			STATUS current
			DESCRIPTION 
				"This object indicates the calibration channel set on the 5 GHz frequency band."
			::= { hwRegulatoryDomainProfileEntry 4 }

		 --1.3.6.1.4.1.2011.6.139.11.1.11.1.5
		hwDcaChannel2GChannelSet OBJECT-TYPE
			SYNTAX OCTET STRING (SIZE (1..256))
			MAX-ACCESS read-write
			STATUS current
			DESCRIPTION 
				"This object indicates the calibration channel set on the 2 GHz frequency band."
			::= { hwRegulatoryDomainProfileEntry 5 }

		 --1.3.6.1.4.1.2011.6.139.11.1.11.1.6
		hwRegulatoryDomainProfilRowStatus OBJECT-TYPE
			SYNTAX RowStatus
			MAX-ACCESS read-write
			STATUS current
			DESCRIPTION 
				"This object indicates the row status of this table. ROWSTATUS_CREATEANDFLOW and ROWSTATUS_DESTROY are commonly used ?	ROWSTATUS_UNDEFINED: undefined ?	ROWSTATUS_ACTIVE: active ?	ROWSTATUS_NOTINSERVICE: notInService ?	ROWSTATUS_NOTREADY: notReady ?	ROWSTATUS_CREATEANDFLOW: createAndGo ?	ROWSTATUS_CREATEANDWAIT: createAndWait ?	ROWSTATUS_DESTROY: destroy."
			::= { hwRegulatoryDomainProfileEntry 6 }

		--1.3.6.1.4.1.2011.6.139.11.1.12
		hwApSystemProfileTable OBJECT-TYPE
			SYNTAX SEQUENCE OF HwApSystemProfileEntry 
			MAX-ACCESS not-accessible
			STATUS current
			DESCRIPTION 
				"This table is used to create or delete an AP system profile and configure AP attributes."
			::= { hwWlanConfigObjects 12 }

		--1.3.6.1.4.1.2011.6.139.11.1.12.1
		hwApSystemProfileEntry OBJECT-TYPE
			SYNTAX HwApSystemProfileEntry 
			MAX-ACCESS not-accessible
			STATUS current
			DESCRIPTION 
				"The index of this table is hwApSystemProfName."
			INDEX { hwApSystemProfName }
			::= { hwApSystemProfileTable 1 }


		HwApSystemProfileEntry ::=
			SEQUENCE {				
				hwApSystemProfName
					OCTET STRING,
				hwApProfStatInterval
					Unsigned32,
				hwApProfSampleTime
					Unsigned32,
				hwApProfLedSwitch
					INTEGER,
				hwApProfMaxStaNum
					Unsigned32,
				hwApProfMtu
					Unsigned32,
				hwApProfMeshRole
					INTEGER,
				hwApProfTemporaryManagement
					INTEGER,
				hwApProfManagementVlan
					Unsigned32,
				hwApProfHighTempThreshold
					Unsigned32,
				hwApProfLowTempThreshold
					Integer32,
				hwApProfOpHRxPowerThreshold
					Unsigned32,
				hwApProfOpLRxPowerThreshold
					Unsigned32,
				hwApProfOpHTempThreshold
					Unsigned32,
				hwApProfOpLTempThreshold
					Integer32,
				hwApProfMemoryUsageThreshold
					Unsigned32,
				hwApProfCpuUsageThreshold
					Unsigned32,
				hwApProfTelnetSwitch
					INTEGER,
				hwApProfSTelnetSwitch
					INTEGER,
				hwApProfConsoleSwitch
					INTEGER,
				hwApProfLogRecordLevel
					INTEGER,
				hwApProfLogServerIp
					IpAddress,
				hwApProfLogServerIpv6
					OCTET STRING,
				hwApProfAlarmRestrictionSwitch
					INTEGER,
				hwApProfAlarmRestrictionPeriod
					Unsigned32,
				hwApProfKeepServiceSwitch
					INTEGER,
				hwApProfProtectPriority
					Unsigned32,
				hwApProfProtectACIp
					IpAddress,
				hwApProfProtectACIpv6
					OCTET STRING,
				hwApProfEapStartMode
					INTEGER,
				hwApProfEapStartTransform
					INTEGER,
				hwApProfEapStartUnicastMac
					MacAddress,
				hwApProfEapResponseMode
					INTEGER,
				hwApProfEapResponseTransform
					INTEGER,
				hwApProfEapResponseUnicastMac
					MacAddress,
				hwApProfLldpRestartDelay
					Unsigned32,
				hwApProfLldpAdminStatus
					INTEGER,
				hwApProfLldpRetransDelay
					Unsigned32,
				hwApProfLldpRetransHoldMultiplier
					Unsigned32,
				hwApProfLldpInterval
					Unsigned32,
				hwApProfLldpReportInterval
					Unsigned32,
				hwApProfStaAccessMode
					INTEGER,
				hwApProfStaAccessModeProfile
					OCTET STRING,
				hwApProfRowStatus
					RowStatus,
				hwApProfSFTPSwitch
				    INTEGER,
				hwApProfDynamicBlackListAgingTime
					Unsigned32,
				hwApProfAntennaOutputMode
				        INTEGER,
				hwApProfMppActiveReselectionSwitch
					INTEGER,
				hwApProfSpectrumServerIPAddress
					IpAddress,
				hwApProfSpectrumServerIPv6Address
					OCTET STRING,
				hwApProfSpectrumServerPort
					Unsigned32,
				hwApProfSpectrumViaACSwitch
					INTEGER,
				hwApProfSpectrumViaACPort
					Unsigned32,
				hwApProfSpectrumNonWifiDeviceAgingTime
					Unsigned32,
				hwApProfPoeMaxPower
					Unsigned32,
				hwApProfPoePowerReserved
					Unsigned32,
				hwApProfPoePowerThreshold
					Unsigned32,
				hwApProfPoeAfInrushSwitch
					INTEGER,
				hwApProfPoeHighInrushSwitch
					INTEGER
			 }

		 --1.3.6.1.4.1.2011.6.139.11.1.12.1.1
		hwApSystemProfName OBJECT-TYPE
			SYNTAX OCTET STRING (SIZE (1..35))
			MAX-ACCESS not-accessible
			STATUS current
			DESCRIPTION 
				"This object indicates the name of an AP system profile. It is the index of the table."
			::= { hwApSystemProfileEntry 1 }


		-- 1.3.6.1.4.1.2011.6.139.11.1.12.1.3
		hwApProfStatInterval OBJECT-TYPE
			SYNTAX Unsigned32 (60..900)
			MAX-ACCESS read-write
			STATUS current
			DESCRIPTION 
				"Description."
			::= { hwApSystemProfileEntry 3 }

		 --1.3.6.1.4.1.2011.6.139.11.1.12.1.4
		hwApProfSampleTime OBJECT-TYPE
			SYNTAX Unsigned32 (2..300)
			MAX-ACCESS read-write
			STATUS current
			DESCRIPTION 
				"This object indicates the sampling interval for the AC to collecting AP performance data. The default value is 30. It is expressed in seconds."
			::= { hwApSystemProfileEntry 4 }

		 --1.3.6.1.4.1.2011.6.139.11.1.12.1.5
		hwApProfLedSwitch OBJECT-TYPE
			SYNTAX INTEGER
				{
				off(1),
				on(2)
				}
			MAX-ACCESS read-write
			STATUS current
			DESCRIPTION 
				"This object indicates whether to enable the AP's LED indicator. The default value is 2."
			::= { hwApSystemProfileEntry 5 }

		 --1.3.6.1.4.1.2011.6.139.11.1.12.1.6
		hwApProfMaxStaNum OBJECT-TYPE
			SYNTAX Unsigned32 (1..256)
			MAX-ACCESS read-write
			STATUS current
			DESCRIPTION 
				"This object indicates the maximum number of access users on an AP. The default value is 128."
			::= { hwApSystemProfileEntry 6 }

		 --1.3.6.1.4.1.2011.6.139.11.1.12.1.7
		hwApProfMtu OBJECT-TYPE
			SYNTAX Unsigned32 (128..1700)
			MAX-ACCESS read-write
			STATUS current
			DESCRIPTION 
				"This object indicates the MTU of an AP interface. The default value is 1500."
			::= { hwApSystemProfileEntry 7 }

		 --1.3.6.1.4.1.2011.6.139.11.1.12.1.8
		hwApProfMeshRole OBJECT-TYPE
			SYNTAX INTEGER
				{
				mpp(1),
				mp(2)
				}
			MAX-ACCESS read-write
			STATUS current
			DESCRIPTION 
				"This object indicates a Mesh role. The default value is 1."
			::= { hwApSystemProfileEntry 8 }

		 --1.3.6.1.4.1.2011.6.139.11.1.12.1.9
		hwApProfTemporaryManagement OBJECT-TYPE
			SYNTAX INTEGER
				{
				disable(1),
				enable(2)
				}
			MAX-ACCESS read-write
			STATUS current
			DESCRIPTION 
				"This object indicates the status of the AP-based offline VAP switch. The default value is 1."
			::= { hwApSystemProfileEntry 9 }

		 --1.3.6.1.4.1.2011.6.139.11.1.12.1.10
		hwApProfManagementVlan OBJECT-TYPE
			SYNTAX Unsigned32 (1..4094|4294967295)
			MAX-ACCESS read-write
			STATUS current
			DESCRIPTION 
				"This object indicates the management VLAN for APs. The default value is 1."
			::= { hwApSystemProfileEntry 10 }

		 --1.3.6.1.4.1.2011.6.139.11.1.12.1.11
		hwApProfHighTempThreshold OBJECT-TYPE
			SYNTAX Unsigned32 (20..110|4294967295)
			MAX-ACCESS read-write
			STATUS current
			DESCRIPTION 
				"This object indicates the high temperature alarm threshold on an AP. The default value 0xFFFFFFFF indicates the system threshold of the AP NOTE System thresholds vary with different AP types. For details, see AP device information."
			::= { hwApSystemProfileEntry 11 }

		 --1.3.6.1.4.1.2011.6.139.11.1.12.1.12
		hwApProfLowTempThreshold OBJECT-TYPE
			SYNTAX Integer32 (-70..10|65535)
			MAX-ACCESS read-write
			STATUS current
			DESCRIPTION 
				"This object indicates the low temperature alarm threshold on an AP. The default value 0xFFFF indicates the system threshold of the AP."
			::= { hwApSystemProfileEntry 12 }

		 --1.3.6.1.4.1.2011.6.139.11.1.12.1.13
		hwApProfOpHRxPowerThreshold OBJECT-TYPE
			SYNTAX Unsigned32 (1000..65535)
			MAX-ACCESS read-write
			STATUS current
			DESCRIPTION 
				"This object indicates the high power threshold of an optical module. The default value is 1000."
			::= { hwApSystemProfileEntry 13 }

		 --1.3.6.1.4.1.2011.6.139.11.1.12.1.14
		hwApProfOpLRxPowerThreshold OBJECT-TYPE
			SYNTAX Unsigned32 (1..250)
			MAX-ACCESS read-write
			STATUS current
			DESCRIPTION 
				"This object indicates the low power threshold of an optical module. The default value is 50."
			::= { hwApSystemProfileEntry 14 }

		 --1.3.6.1.4.1.2011.6.139.11.1.12.1.15
		hwApProfOpHTempThreshold OBJECT-TYPE
			SYNTAX Unsigned32 (70..125)
			MAX-ACCESS read-write
			STATUS current
			DESCRIPTION 
				"This object indicates the high temperature threshold of an optical module. The default value is 70."
			::= { hwApSystemProfileEntry 15 }

		 --1.3.6.1.4.1.2011.6.139.11.1.12.1.16
		hwApProfOpLTempThreshold OBJECT-TYPE
			SYNTAX Integer32 (-40..-5)
			MAX-ACCESS read-write
			STATUS current
			DESCRIPTION 
				"This object indicates the low temperature threshold of an optical module. The default value is -5."
			::= { hwApSystemProfileEntry 16 }

		 --1.3.6.1.4.1.2011.6.139.11.1.12.1.17
		hwApProfMemoryUsageThreshold OBJECT-TYPE
			SYNTAX Unsigned32 (30..100)
			MAX-ACCESS read-write
			STATUS current
			DESCRIPTION 
				"This object indicates the memory usage alarm threshold of an AP. The default value is 80. It is expressed in percentage."
			::= { hwApSystemProfileEntry 17 }

		 --1.3.6.1.4.1.2011.6.139.11.1.12.1.18
		hwApProfCpuUsageThreshold OBJECT-TYPE
			SYNTAX Unsigned32 (50..100)
			MAX-ACCESS read-write
			STATUS current
			DESCRIPTION 
				"This object indicates the CPU usage alarm threshold of an AP. The default value is 90. It is expressed in percentage."
			::= { hwApSystemProfileEntry 18 }

		 --1.3.6.1.4.1.2011.6.139.11.1.12.1.19
		hwApProfTelnetSwitch OBJECT-TYPE
			SYNTAX INTEGER
				{
				disable(1),
				enable(2)
				}
			MAX-ACCESS read-write
			STATUS current
			DESCRIPTION 
				"This object indicates whether to enable Telnet. The default value is 1."
			::= { hwApSystemProfileEntry 19 }

		 --1.3.6.1.4.1.2011.6.139.11.1.12.1.20
		hwApProfSTelnetSwitch OBJECT-TYPE
			SYNTAX INTEGER
				{
				disable(1),
				enable(2)
				}
			MAX-ACCESS read-write
			STATUS current
			DESCRIPTION 
				"This object indicates whether to enable SSH. The default value is 2."
			::= { hwApSystemProfileEntry 20 }

		 --1.3.6.1.4.1.2011.6.139.11.1.12.1.21
		hwApProfConsoleSwitch OBJECT-TYPE
			SYNTAX INTEGER
				{
				disable(1),
				enable(2)
				}
			MAX-ACCESS read-write
			STATUS current
			DESCRIPTION 
				"This object indicates whether to enable the console. The default value is 2."
			::= { hwApSystemProfileEntry 21 }

		 --1.3.6.1.4.1.2011.6.139.11.1.12.1.22
		hwApProfLogRecordLevel OBJECT-TYPE
			SYNTAX INTEGER
				{
				emergency(1),
				alert(2),
				critical(3),
				error(4),
				warning(5),
				notice(6),
				info(7),
				debug(8)
				}
			MAX-ACCESS read-write
			STATUS current
			DESCRIPTION 
				"This object indicates the log backup level. The default value is 7."
			::= { hwApSystemProfileEntry 22 }

		 --1.3.6.1.4.1.2011.6.139.11.1.12.1.23
		hwApProfLogServerIp OBJECT-TYPE
			SYNTAX IpAddress
			MAX-ACCESS read-write
			STATUS current
			DESCRIPTION 
				"This object indicates the IP address of the log server."
			::= { hwApSystemProfileEntry 23 }

		 --1.3.6.1.4.1.2011.6.139.11.1.12.1.24
		hwApProfLogServerIpv6 OBJECT-TYPE
			SYNTAX OCTET STRING
			MAX-ACCESS read-write
			STATUS current
			DESCRIPTION 
				"This object indicates the IPv6 address of the log server."
			::= { hwApSystemProfileEntry 24 }

		 --1.3.6.1.4.1.2011.6.139.11.1.12.1.25
		hwApProfAlarmRestrictionSwitch OBJECT-TYPE
			SYNTAX INTEGER
				{
				disable(1),
				enable(2)
				}
			MAX-ACCESS read-write
			STATUS current
			DESCRIPTION 
				"This object indicates the status of the alarm suppression switch. The default value is 2."
			::= { hwApSystemProfileEntry 25 }

		 --1.3.6.1.4.1.2011.6.139.11.1.12.1.26
		hwApProfAlarmRestrictionPeriod OBJECT-TYPE
			SYNTAX Unsigned32 (10..300)
			MAX-ACCESS read-write
			STATUS current
			DESCRIPTION 
				"This object indicates the alarm suppression period. The default value is 60 seconds."
			::= { hwApSystemProfileEntry 26 }

		 --1.3.6.1.4.1.2011.6.139.11.1.12.1.27
		hwApProfKeepServiceSwitch OBJECT-TYPE
			SYNTAX INTEGER
				{
				enable(1) ,
				disable(2) ,
				allowaccess(3)
				}
			MAX-ACCESS read-write
			STATUS current
			DESCRIPTION 
				"This object indicates whether to enable the offline service retaining function. The default value is 2."
			::= { hwApSystemProfileEntry 27 }

		 --1.3.6.1.4.1.2011.6.139.11.1.12.1.28
		hwApProfProtectPriority OBJECT-TYPE
			SYNTAX Unsigned32 (0..7|4294967295)
			MAX-ACCESS read-write
			STATUS current
			DESCRIPTION 
				"This object indicates the AC priority. A smaller value indicates a higher priority. The default value 0xFFFFFFFF indicates that no priority is configured."
			::= { hwApSystemProfileEntry 28 }

		 --1.3.6.1.4.1.2011.6.139.11.1.12.1.29
		hwApProfProtectACIp OBJECT-TYPE
			SYNTAX IpAddress
			MAX-ACCESS read-write
			STATUS current
			DESCRIPTION 
				"This object indicates the IP address of the standby AC."
			::= { hwApSystemProfileEntry 29 }

		 --1.3.6.1.4.1.2011.6.139.11.1.12.1.30
		hwApProfProtectACIpv6 OBJECT-TYPE
			SYNTAX OCTET STRING
			MAX-ACCESS read-write
			STATUS current
			DESCRIPTION 
				"This object indicates the IPv6 address of the standby AC."
			::= { hwApSystemProfileEntry 30 }

		 --1.3.6.1.4.1.2011.6.139.11.1.12.1.31
		hwApProfEapStartMode OBJECT-TYPE
			SYNTAX INTEGER
				{
				broadcast(1),
				multicast(2),
				unicast(3)
				}
			MAX-ACCESS read-write
			STATUS current
			DESCRIPTION 
				"This object indicates the EAP Start packet conversion mode. The default value is 2."
			::= { hwApSystemProfileEntry 31 }

		 --1.3.6.1.4.1.2011.6.139.11.1.12.1.32
		hwApProfEapStartTransform OBJECT-TYPE
			SYNTAX INTEGER
				{
				equalBssid(1) ,
				always(2)
				}
			MAX-ACCESS read-write
			STATUS current
			DESCRIPTION 
				"This object indicates the EAP Start packet conversion mode. The default value is 2."
			::= { hwApSystemProfileEntry 32 }

		 --1.3.6.1.4.1.2011.6.139.11.1.12.1.33
		hwApProfEapStartUnicastMac OBJECT-TYPE
			SYNTAX MacAddress
			MAX-ACCESS read-write
			STATUS current
			DESCRIPTION 
				"This object indicates that EAP Start packets are converted to those with specific MAC addresses."
			::= { hwApSystemProfileEntry 33 }

		 --1.3.6.1.4.1.2011.6.139.11.1.12.1.34
		hwApProfEapResponseMode OBJECT-TYPE
			SYNTAX INTEGER
				{
				broadcast(1),
				multicast(2) ,
				specific(3),
				learnling(4)
				
				}
			MAX-ACCESS read-write
			STATUS current
			DESCRIPTION 
				"This object indicates the EAP Response packet conversion mode. The default value is 2."
			::= { hwApSystemProfileEntry 34 }

		 --1.3.6.1.4.1.2011.6.139.11.1.12.1.35
		hwApProfEapResponseTransform OBJECT-TYPE
			SYNTAX INTEGER
				{
				equalBssid(1) ,
				always(2)
				}
			MAX-ACCESS read-write
			STATUS current
			DESCRIPTION 
				"This object indicates the EAP Response packet conversion mode. The default value is 4."
			::= { hwApSystemProfileEntry 35 }

		 --1.3.6.1.4.1.2011.6.139.11.1.12.1.36
		hwApProfEapResponseUnicastMac OBJECT-TYPE
			SYNTAX MacAddress
			MAX-ACCESS read-write
			STATUS current
			DESCRIPTION 
				"This object indicates that EAP Response packets are converted to those with specific MAC addresses."
			::= { hwApSystemProfileEntry 36 }

		 --1.3.6.1.4.1.2011.6.139.11.1.12.1.37
		hwApProfLldpRestartDelay OBJECT-TYPE
			SYNTAX Unsigned32 (1..10)
			MAX-ACCESS read-write
			STATUS current
			DESCRIPTION 
				"This object indicates the delay for re-enabling LLDP. The default value is 2. It is expressed in seconds."
			::= { hwApSystemProfileEntry 37 }

		 --1.3.6.1.4.1.2011.6.139.11.1.12.1.38
		hwApProfLldpAdminStatus OBJECT-TYPE
			SYNTAX INTEGER
				{
				txrx(1),
				rx(2),
				tx(3)
				}
			MAX-ACCESS read-write
			STATUS current
			DESCRIPTION 
				"This object indicates the operation mode of LLDP. The default value is 1."
			::= { hwApSystemProfileEntry 38 }

		 --1.3.6.1.4.1.2011.6.139.11.1.12.1.39
		hwApProfLldpRetransDelay OBJECT-TYPE
			SYNTAX Unsigned32 (1..8192)
			MAX-ACCESS read-write
			STATUS current
			DESCRIPTION 
				"This object indicates the message retransmitting delay. The default value is 2. It is expressed in seconds."
			::= { hwApSystemProfileEntry 39 }

		 --1.3.6.1.4.1.2011.6.139.11.1.12.1.40
		hwApProfLldpRetransHoldMultiplier OBJECT-TYPE
			SYNTAX Unsigned32 (2..10)
			MAX-ACCESS read-write
			STATUS current
			DESCRIPTION 
				"This object indicates the hold time multiplier of device information on neighbors (cardinal number is the interval time). The default value is 4."
			::= { hwApSystemProfileEntry 40 }

		 --1.3.6.1.4.1.2011.6.139.11.1.12.1.41
		hwApProfLldpInterval OBJECT-TYPE
			SYNTAX Unsigned32 (5..32768)
			MAX-ACCESS read-write
			STATUS current
			DESCRIPTION 
				"This object indicates the interval at which LLDP packets are sent. The default value is 30 seconds."
			::= { hwApSystemProfileEntry 41 }

		 --1.3.6.1.4.1.2011.6.139.11.1.12.1.42
		hwApProfLldpReportInterval OBJECT-TYPE
			SYNTAX Unsigned32 (5..3600)
			MAX-ACCESS read-write
			STATUS current
			DESCRIPTION 
				"This object indicates the interval at which LLDP packets are reported. The default value is 30 seconds."
			::= { hwApSystemProfileEntry 42 }

		 --1.3.6.1.4.1.2011.6.139.11.1.12.1.43
		hwApProfStaAccessMode OBJECT-TYPE
			SYNTAX INTEGER
				{
				unknown(-1) ,
				disable(1) ,
				blacklist(2) ,
				whitelist(3)
				}
			MAX-ACCESS read-write
			STATUS current
			DESCRIPTION 
				"This object indicates the access mode. The default value is 1."
			::= { hwApSystemProfileEntry 43 }

		 --1.3.6.1.4.1.2011.6.139.11.1.12.1.44
		hwApProfStaAccessModeProfile OBJECT-TYPE
			SYNTAX OCTET STRING (SIZE (0..35))
			MAX-ACCESS read-write
			STATUS current
			DESCRIPTION 
				"This object indicates blacklist and whitelist profiles."
			::= { hwApSystemProfileEntry 44 }

		 --1.3.6.1.4.1.2011.6.139.11.1.12.1.45
		hwApProfRowStatus OBJECT-TYPE
			SYNTAX RowStatus
			MAX-ACCESS read-write
			STATUS current
			DESCRIPTION 
				"This object indicates the row status of this table. ROWSTATUS_CREATEANDFLOW and ROWSTATUS_DESTROY are commonly used ?	ROWSTATUS_UNDEFINED: undefined ?	ROWSTATUS_ACTIVE: active ?	ROWSTATUS_NOTINSERVICE: notInService ?	ROWSTATUS_NOTREADY: notReady ?	ROWSTATUS_CREATEANDFLOW: createAndGo ?	ROWSTATUS_CREATEANDWAIT: createAndWait ?	ROWSTATUS_DESTROY: destroy."
			::= { hwApSystemProfileEntry 45 }
			
		--1.3.6.1.4.1.2011.6.139.11.1.12.1.46
		hwApProfSFTPSwitch OBJECT-TYPE
			SYNTAX INTEGER
				{
				disable(1),
				enable(2)
				}
			MAX-ACCESS read-write
			STATUS current
			DESCRIPTION 
				"This object indicates whether to enable the SFTP. The default value is 2."
			::= { hwApSystemProfileEntry 46 }
			
		--1.3.6.1.4.1.2011.6.139.11.1.12.1.47
		hwApProfDynamicBlackListAgingTime OBJECT-TYPE
            SYNTAX Unsigned32 (180..3600)
			MAX-ACCESS read-write
			STATUS current
			DESCRIPTION 
				"This object indicates the aging time of the dynamic blacklist entries. The default value is 600."
			::= { hwApSystemProfileEntry 47 }

                --1.3.6.1.4.1.2011.6.139.11.1.12.1.48
		hwApProfAntennaOutputMode OBJECT-TYPE
			SYNTAX INTEGER
				{
				combine(1),
				split(2)
				}
			MAX-ACCESS read-write
			STATUS current
			DESCRIPTION 
				"Description."
			::= { hwApSystemProfileEntry 48 }
			
		-- 1.3.6.1.4.1.2011.6.139.11.1.12.1.49
		hwApProfMppActiveReselectionSwitch OBJECT-TYPE
			SYNTAX INTEGER
				{
				disable(1),
				enable(2)
				}
			MAX-ACCESS read-write
			STATUS current
			DESCRIPTION
				"This object indicates of mpp active reselection."
			::= { hwApSystemProfileEntry 49 }

		

		-- 1.3.6.1.4.1.2011.6.139.11.1.12.1.50
		hwApProfSpectrumServerIPAddress OBJECT-TYPE
			SYNTAX IpAddress
			MAX-ACCESS read-write
			STATUS current
			DESCRIPTION
				"This object indicates the IPv6 address of the spectrum analysis server. You choose an IPv4 or IPv6 address. By default, the IPv4 address 255.255.255.255 is used."
			::= { hwApSystemProfileEntry 50 }

		

		-- 1.3.6.1.4.1.2011.6.139.11.1.12.1.51
		hwApProfSpectrumServerIPv6Address OBJECT-TYPE
			SYNTAX OCTET STRING
			MAX-ACCESS read-write
			STATUS current
			DESCRIPTION
				"This object indicates the IPv6 address of the spectrum analysis server. You choose an IPv4 or IPv6 address. By default, it is not configured."
			::= { hwApSystemProfileEntry 51 }

		

		-- 1.3.6.1.4.1.2011.6.139.11.1.12.1.52
		hwApProfSpectrumServerPort OBJECT-TYPE
			SYNTAX Unsigned32 (0 | 5000..65535)
			MAX-ACCESS read-write
			STATUS current
			DESCRIPTION
				"This object indicates the port of the spectrum analysis server. The default value is 32181."
			::= { hwApSystemProfileEntry 52 }

		

		-- 1.3.6.1.4.1.2011.6.139.11.1.12.1.53
		hwApProfSpectrumViaACSwitch OBJECT-TYPE
			SYNTAX INTEGER
				{
				disable(1),
				enable(2)
				}
			MAX-ACCESS read-write
			STATUS current
			DESCRIPTION
				"This object indicates the status of the spectrum analysis function. The default value is 2."
			::= { hwApSystemProfileEntry 53 }

		

		-- 1.3.6.1.4.1.2011.6.139.11.1.12.1.54
		hwApProfSpectrumViaACPort OBJECT-TYPE
			SYNTAX Unsigned32 (0 | 5000..65535)
			MAX-ACCESS read-write
			STATUS current
			DESCRIPTION
				"This object indicates the port number used by the AP to report spectrum analysis data to the AC. The default value is 6412."
			::= { hwApSystemProfileEntry 54 }

		

		-- 1.3.6.1.4.1.2011.6.139.11.1.12.1.55
		hwApProfSpectrumNonWifiDeviceAgingTime OBJECT-TYPE
			SYNTAX Unsigned32 (1..30)
			MAX-ACCESS read-write
			STATUS current
			DESCRIPTION
				"This object indicates the aging time of non-WLAN devices on the AC. The default value is 3 minutes."
			::= { hwApSystemProfileEntry 55 }

		
		-- 1.3.6.1.4.1.2011.6.139.11.1.12.1.56
		hwApProfPoeMaxPower OBJECT-TYPE
			SYNTAX Unsigned32 (15400..380000)
			MAX-ACCESS read-write
			STATUS current
			DESCRIPTION
				"This object indicates the maximum output power of the AP.The default value is 380000."
			::= { hwApSystemProfileEntry 56 }

		
		-- 1.3.6.1.4.1.2011.6.139.11.1.12.1.57
		hwApProfPoePowerReserved OBJECT-TYPE
			SYNTAX Unsigned32 (0..100)
			MAX-ACCESS read-write
			STATUS current
			DESCRIPTION
				"This object indicates the percentage of reserved PoE power to the available PoE power.The default value is 0."
			::= { hwApSystemProfileEntry 57 }

		
		-- 1.3.6.1.4.1.2011.6.139.11.1.12.1.58
		hwApProfPoePowerThreshold OBJECT-TYPE
			SYNTAX Unsigned32 (0..100)
			MAX-ACCESS read-write
			STATUS current
			DESCRIPTION
				"This object indicates the alarm threshold of PoE power consumption percentage.The default value is 100."
			::= { hwApSystemProfileEntry 58 }

		
		-- 1.3.6.1.4.1.2011.6.139.11.1.12.1.59
		hwApProfPoeAfInrushSwitch OBJECT-TYPE
			SYNTAX INTEGER
				{
				disable(1),
				enable(2)
				}
			MAX-ACCESS read-write
			STATUS current
			DESCRIPTION
				"This object indicates whether to enable the IEEE 802.3at-compliant device to provide power in accordance with IEEE 802.3af.The default value is 1."
			::= { hwApSystemProfileEntry 59 }

		
		-- 1.3.6.1.4.1.2011.6.139.11.1.12.1.60
		hwApProfPoeHighInrushSwitch OBJECT-TYPE
			SYNTAX INTEGER
				{
				disable(1),
				enable(2)
				}
			MAX-ACCESS read-write
			STATUS current
			DESCRIPTION
				"This object indicates whether to enable the device to allow high inrush current during power-on.The default value is 1."
			::= { hwApSystemProfileEntry 60 }

		

		-- 1.3.6.1.4.1.2011.6.139.11.1.13
		hwAPWiredPortProfileTable OBJECT-TYPE
			SYNTAX SEQUENCE OF HwAPWiredPortProfileEntry 
			MAX-ACCESS not-accessible
			STATUS current
			DESCRIPTION 
				"This table is used to create or delete an AP wired port link profile and modify or query attributes."
			::= { hwWlanConfigObjects 13 }

		--1.3.6.1.4.1.2011.6.139.11.1.13.1
		hwAPWiredPortProfileEntry OBJECT-TYPE
			SYNTAX HwAPWiredPortProfileEntry 
			MAX-ACCESS not-accessible
			STATUS current
			DESCRIPTION 
				"The index of this table is hwAPWiredPortProfileName."
			INDEX { hwAPWiredPortProfileName }
			::= { hwAPWiredPortProfileTable 1 }


		HwAPWiredPortProfileEntry ::=
			SEQUENCE {				
				hwAPWiredPortProfileName
					OCTET STRING,
				hwAPWiredPortPortLinkProfileName
					OCTET STRING,
				hwAPWiredPortProfilePortDesc
					OCTET STRING,
				hwAPWiredPortProfilePortEthTrunkID
					Unsigned32,
				hwAPWiredPortProfilePortSTPSwitch
					INTEGER,
				hwAPWiredPortProfilePortMode
					INTEGER,
				hwAPWiredPortProfilePortVlanPvid
					Unsigned32,
				hwAPWiredPortProfilePortVlanTagged
					OCTET STRING,
				hwAPWiredPortProfilePortVlanUntagged
					OCTET STRING,
				hwAPWiredPortProfileUserIsolate
					INTEGER,
				hwAPWiredPortProfileDhcpTrust
					INTEGER,
				hwAPWiredPortProfileNdTrust
					INTEGER,
				hwAPWiredPortProfileRowStatus
					RowStatus,
				hwAPWiredPortProfileLearnAddress
					INTEGER,
				hwAPWiredPortProfileIpBindCheck
					INTEGER,
				hwAPWiredPortProfileArpBindCheck
					INTEGER,
				hwAPWiredPortProfileSTPAutoShutdown
					INTEGER,
				hwAPWiredPortProfileSTPAutoShutdownRecoveryTime
					Unsigned32,
				hwAPWiredPortProfileTrafficOptimizeSuppressionBc
					Unsigned32,
				hwAPWiredPortProfileTrafficOptimizeSuppressionUc
					Unsigned32,
				hwAPWiredPortProfileTrafficOptimizeSuppressionMc
					Unsigned32
			 }

		 --1.3.6.1.4.1.2011.6.139.11.1.13.1.1
		hwAPWiredPortProfileName OBJECT-TYPE
			SYNTAX OCTET STRING (SIZE (1..35))
			MAX-ACCESS not-accessible
			STATUS current
			DESCRIPTION 
				"This object indicates the name of an AP wired port link profile."
			::= { hwAPWiredPortProfileEntry 1 }

		 --1.3.6.1.4.1.2011.6.139.11.1.13.1.2
		hwAPWiredPortPortLinkProfileName OBJECT-TYPE
			SYNTAX OCTET STRING (SIZE (1..35))
			MAX-ACCESS read-write
			STATUS current
			DESCRIPTION 
				"This object indicates the bound AP wired port link profile."
			::= { hwAPWiredPortProfileEntry 2 }

		 --1.3.6.1.4.1.2011.6.139.11.1.13.1.3
		hwAPWiredPortProfilePortDesc OBJECT-TYPE
			SYNTAX OCTET STRING (SIZE (0..31))
			MAX-ACCESS read-write
			STATUS current
			DESCRIPTION 
				"This object indicates the description of an interface."
			::= { hwAPWiredPortProfileEntry 3 }

		 --1.3.6.1.4.1.2011.6.139.11.1.13.1.4
		hwAPWiredPortProfilePortEthTrunkID OBJECT-TYPE
			SYNTAX Unsigned32 (0 | 255)
			MAX-ACCESS read-write
			STATUS current
			DESCRIPTION 
				"This object indicates the ID of a Trunk. 0 is valid and 0xFFFFFFFF is invalid. The default value is 0xFFFFFFFF."
			::= { hwAPWiredPortProfileEntry 4 }

		 --1.3.6.1.4.1.2011.6.139.11.1.13.1.5
		hwAPWiredPortProfilePortSTPSwitch OBJECT-TYPE
			SYNTAX INTEGER
				{
				disable(1),
				enable(2)
				}
			MAX-ACCESS read-write
			STATUS current
			DESCRIPTION 
				"This object indicates whether to enable STP on wired ports. The default value is 1."
			::= { hwAPWiredPortProfileEntry 5 }

		 --1.3.6.1.4.1.2011.6.139.11.1.13.1.6
		hwAPWiredPortProfilePortMode OBJECT-TYPE
			SYNTAX INTEGER
				{
				root(1),
				endpoint(2),
				middle(3),
				null(256)
				}
			MAX-ACCESS read-write
			STATUS current
			DESCRIPTION 
				"This object indicates the mode of the wired port. For FE ports of plate APs, the default value is 2. For other ports, the default value is 1."
			::= { hwAPWiredPortProfileEntry 6 }

		 --1.3.6.1.4.1.2011.6.139.11.1.13.1.7
		hwAPWiredPortProfilePortVlanPvid OBJECT-TYPE
			SYNTAX Unsigned32 (0..4094)
			MAX-ACCESS read-write
			STATUS current
			DESCRIPTION 
				"This object indicates the PVID of a port. The default value is 1."
			::= { hwAPWiredPortProfileEntry 7 }

		 --1.3.6.1.4.1.2011.6.139.11.1.13.1.8
		hwAPWiredPortProfilePortVlanTagged OBJECT-TYPE
			SYNTAX OCTET STRING (SIZE (0..1024))
			MAX-ACCESS read-write
			STATUS current
			DESCRIPTION 
				"This object indicates whether to tag ports with VLAN IDs. The default value is 0."
			::= { hwAPWiredPortProfileEntry 8 }

		 --1.3.6.1.4.1.2011.6.139.11.1.13.1.9
		hwAPWiredPortProfilePortVlanUntagged OBJECT-TYPE
			SYNTAX OCTET STRING (SIZE (0..1024))
			MAX-ACCESS read-write
			STATUS current
			DESCRIPTION 
				"This object indicates whether to untag VLAN IDS from ports. The default value is 1."
			::= { hwAPWiredPortProfileEntry 9 }

		 --1.3.6.1.4.1.2011.6.139.11.1.13.1.10
		hwAPWiredPortProfileUserIsolate OBJECT-TYPE
			SYNTAX INTEGER
				{
				disable(1) ,
				l3Isolate(2),
				l2Isolate(3)
				}
			MAX-ACCESS read-write
			STATUS current
			DESCRIPTION 
				"This object indicates the status of the user isolation function. The default value is 1."
			::= { hwAPWiredPortProfileEntry 10 }

		 --1.3.6.1.4.1.2011.6.139.11.1.13.1.11
		hwAPWiredPortProfileDhcpTrust OBJECT-TYPE
			SYNTAX INTEGER
				{
				disable(1) ,
				enable(2)
				}
			MAX-ACCESS read-write
			STATUS current
			DESCRIPTION 
				"This object indicates whether a port is configured as a DHCP trusted port. The default value is 1."
			::= { hwAPWiredPortProfileEntry 11 }

		 --1.3.6.1.4.1.2011.6.139.11.1.13.1.12
		hwAPWiredPortProfileNdTrust OBJECT-TYPE
			SYNTAX INTEGER
				{
				disable(1) ,
				enable(2)
				}
			MAX-ACCESS read-write
			STATUS current
			DESCRIPTION 
				"This object indicates whether a port is configured as a ND trusted port. The default value is 1."
			::= { hwAPWiredPortProfileEntry 12 }

		 --1.3.6.1.4.1.2011.6.139.11.1.13.1.13
		hwAPWiredPortProfileRowStatus OBJECT-TYPE
			SYNTAX RowStatus
			MAX-ACCESS read-create
			STATUS current
			DESCRIPTION 
				"This object indicates the row status of this table. ROWSTATUS_CREATEANDFLOW and ROWSTATUS_DESTROY are commonly used."
			::= { hwAPWiredPortProfileEntry 13 }

		-- 1.3.6.1.4.1.2011.6.139.11.1.13.1.14
		hwAPWiredPortProfileLearnAddress OBJECT-TYPE
			SYNTAX INTEGER
				{
				disable(1),
				enable(2)
				}
			MAX-ACCESS read-write
			STATUS current
			DESCRIPTION
				"This object indicates whether to enable address learning.The default value is 1."
			::= { hwAPWiredPortProfileEntry 14 }

		-- 1.3.6.1.4.1.2011.6.139.11.1.13.1.15
		hwAPWiredPortProfileIpBindCheck OBJECT-TYPE
			SYNTAX INTEGER
				{
				disable(1),
				enable(2)
				}
			MAX-ACCESS read-write
			STATUS current
			DESCRIPTION
				"This object indicates whether to enable IP packet checking against the binding table.The default value is 1."
			::= { hwAPWiredPortProfileEntry 15 }

		-- 1.3.6.1.4.1.2011.6.139.11.1.13.1.16
		hwAPWiredPortProfileArpBindCheck OBJECT-TYPE
			SYNTAX INTEGER
				{
				disable(1),
				enable(2)
				}
			MAX-ACCESS read-write
			STATUS current
			DESCRIPTION
				"This object indicates whether to enable ARP packet checking against the binding table.The default value is 1."
			::= { hwAPWiredPortProfileEntry 16 }

		-- 1.3.6.1.4.1.2011.6.139.11.1.13.1.17
		hwAPWiredPortProfileSTPAutoShutdown OBJECT-TYPE
			SYNTAX INTEGER
				{
				disable(1),
				enable(2)
				}
			MAX-ACCESS read-write
			STATUS current
			DESCRIPTION
				"This object indicates whether to enable STP-triggered port shutdown.The default value is 1."
			::= { hwAPWiredPortProfileEntry 17 }

		-- 1.3.6.1.4.1.2011.6.139.11.1.13.1.18
		hwAPWiredPortProfileSTPAutoShutdownRecoveryTime OBJECT-TYPE
			SYNTAX Unsigned32 (600..3600)
			MAX-ACCESS read-write
			STATUS current
			DESCRIPTION
				"This object indicates the automatic port recovery time after an STP-triggered shutdown.The default value is 600."
			::= { hwAPWiredPortProfileEntry 18 }

		-- 1.3.6.1.4.1.2011.6.139.11.1.13.1.19
		hwAPWiredPortProfileTrafficOptimizeSuppressionBc OBJECT-TYPE
			SYNTAX Unsigned32 (0..14881000)
			MAX-ACCESS read-write
			STATUS current
			DESCRIPTION
				"This object indicates the rate limit for broadcast storm suppression.The default value is 0xFFFFFFFF."
			::= { hwAPWiredPortProfileEntry 19 }

		-- 1.3.6.1.4.1.2011.6.139.11.1.13.1.20
		hwAPWiredPortProfileTrafficOptimizeSuppressionUc OBJECT-TYPE
			SYNTAX Unsigned32 (0..14881000)
			MAX-ACCESS read-write
			STATUS current
			DESCRIPTION
				"This object indicates the rate limit for unknown unicast storm suppression.The default value is 0xFFFFFFFF."
			::= { hwAPWiredPortProfileEntry 20 }

		-- 1.3.6.1.4.1.2011.6.139.11.1.13.1.21
		hwAPWiredPortProfileTrafficOptimizeSuppressionMc OBJECT-TYPE
			SYNTAX Unsigned32 (0..14881000)
			MAX-ACCESS read-write
			STATUS current
			DESCRIPTION
				"This object indicates the rate limit for multicast storm suppression.The default value is 0xFFFFFFFF."
			::= { hwAPWiredPortProfileEntry 21 }

		--1.3.6.1.4.1.2011.6.139.11.1.14
		hwAPWiredPortProfileTrafficFilterTable OBJECT-TYPE
			SYNTAX SEQUENCE OF HwAPWiredPortProfileTrafficFilterEntry 
			MAX-ACCESS not-accessible
			STATUS current
			DESCRIPTION 
				"This table is used to configure ACL-based packet filtering in an AP wired port profile."
			::= { hwWlanConfigObjects 14 }

		--1.3.6.1.4.1.2011.6.139.11.1.14.1
		hwAPWiredPortProfileTrafficFilterEntry OBJECT-TYPE
			SYNTAX HwAPWiredPortProfileTrafficFilterEntry 
			MAX-ACCESS not-accessible
			STATUS current
			DESCRIPTION 
				"Indexes of this table are hwAPWiredPortProfileName."
			INDEX { hwAPWiredPortProfileName, hwAPWiredPortProfileTrafficFilterType,hwAPWiredPortProfileTrafficFilterDirection }
			::= { hwAPWiredPortProfileTrafficFilterTable 1 }


		HwAPWiredPortProfileTrafficFilterEntry ::=
			SEQUENCE {				
				hwAPWiredPortProfileTrafficFilterDirection
					INTEGER,
				hwAPWiredPortProfileTrafficFilterType
					INTEGER,
				hwAPWiredPortProfileTrafficFilterAclID
					Integer32,
				hwAPWiredPortProfileTrafficFilterRowStatus
				        RowStatus
			 }

		 --1.3.6.1.4.1.2011.6.139.11.1.14.1.1
		hwAPWiredPortProfileTrafficFilterDirection OBJECT-TYPE
			SYNTAX INTEGER
				{
				inbound(1),
				outbound(2)
				}
			MAX-ACCESS not-accessible
			STATUS current
			DESCRIPTION 
				"This object indicates the direction of the ACL-based packet filtering."
			::= { hwAPWiredPortProfileTrafficFilterEntry 1 }

		 --1.3.6.1.4.1.2011.6.139.11.1.14.1.2
		hwAPWiredPortProfileTrafficFilterType OBJECT-TYPE
			SYNTAX INTEGER
				{
				ipv4(1),
				ipv6(2)
				}
			MAX-ACCESS not-accessible
			STATUS current
			DESCRIPTION 
				"This object indicates the type of the ACL-based packet filtering."
			::= { hwAPWiredPortProfileTrafficFilterEntry 2 }

		 --1.3.6.1.4.1.2011.6.139.11.1.14.1.3
		hwAPWiredPortProfileTrafficFilterAclID OBJECT-TYPE
			SYNTAX Integer32 (3000..3031|4000..4031)
			MAX-ACCESS read-write
			STATUS current
			DESCRIPTION 
				"This object indicates ACL rules for packet filtering."
			::= { hwAPWiredPortProfileTrafficFilterEntry 3 }
                
                 --1.3.6.1.4.1.2011.6.139.11.1.14.1.4
		hwAPWiredPortProfileTrafficFilterRowStatus OBJECT-TYPE
			SYNTAX RowStatus
			MAX-ACCESS read-create
			STATUS current
			DESCRIPTION 
				"This object indicates packet filtering rules configured on the wired interface."
			::= { hwAPWiredPortProfileTrafficFilterEntry 4 }
			
		--1.3.6.1.4.1.2011.6.139.11.1.15
		hwAPPortLinkProfileTable OBJECT-TYPE
			SYNTAX SEQUENCE OF HwAPPortLinkProfileEntry 
			MAX-ACCESS not-accessible
			STATUS current
			DESCRIPTION 
				"This table is used to create or delete an AP wired port link profile and configure parameters."
			::= { hwWlanConfigObjects 15 }

		--1.3.6.1.4.1.2011.6.139.11.1.15.1
		hwAPPortLinkProfileEntry OBJECT-TYPE
			SYNTAX HwAPPortLinkProfileEntry 
			MAX-ACCESS not-accessible
			STATUS current
			DESCRIPTION 
				"The index of this table is hwAPPortLinkProfileName."
			INDEX { hwAPPortLinkProfileName }
			::= { hwAPPortLinkProfileTable 1 }


		HwAPPortLinkProfileEntry ::=
			SEQUENCE {				
				hwAPPortLinkProfileName
					OCTET STRING,
				hwAPPortLinkProfileLldpEnable
					INTEGER,
				hwAPPortLinkProfileLldpTlvType
					Unsigned32,
				hwAPPortLinkProfileCrcAlarmEnable
					INTEGER,
				hwAPPortLinkProfileCrcAlarmThreshold
					Unsigned32,
				hwAPPortLinkProfileCrcAlarmResumeThreshold
					Unsigned32,
				hwAPPortLinkProfileRowStatus
					RowStatus,
				hwAPPortLinkProfilePoeSwitch
					INTEGER,
				hwAPPortLinkProfilePoePriority
					INTEGER,
				hwAPPortLinkProfilePoeForcePowerSwitch
					INTEGER,
				hwAPPortLinkProfilePoeLegacySwitch
					INTEGER,
				hwAPPortLinkProfilePoeOffTimeRange
					OCTET STRING,
				hwAPPortLinkProfileAdminStatus
					INTEGER
			 }

		 --1.3.6.1.4.1.2011.6.139.11.1.15.1.1
		hwAPPortLinkProfileName OBJECT-TYPE
			SYNTAX OCTET STRING (SIZE (1..35))
			MAX-ACCESS not-accessible
			STATUS current
			DESCRIPTION 
				"This object indicates the name of an AP wired port link profile."
			::= { hwAPPortLinkProfileEntry 1 }

		 --1.3.6.1.4.1.2011.6.139.11.1.15.1.2
		hwAPPortLinkProfileLldpEnable OBJECT-TYPE
			SYNTAX INTEGER
				{
				disable(1),
				enable(2)
				}
			MAX-ACCESS read-write
			STATUS current
			DESCRIPTION 
				"This object indicates the status of the LLDP function. The default value is 2."
			::= { hwAPPortLinkProfileEntry 2 }

		 --1.3.6.1.4.1.2011.6.139.11.1.15.1.3
		hwAPPortLinkProfileLldpTlvType OBJECT-TYPE
			SYNTAX Unsigned32(0..31)
			MAX-ACCESS read-write
			STATUS current
			DESCRIPTION 
				"This object indicates the types of TLVs that can be advertised from an AP's wired port. The default value is all(0x11) ?	0: invalid ?	bit0: management-address ?	bit1: port-description ?	bit2: system-capability  ?	bit3: system-description ?	bit4: system-name."
			::= { hwAPPortLinkProfileEntry 3 }

		 --1.3.6.1.4.1.2011.6.139.11.1.15.1.4
		hwAPPortLinkProfileCrcAlarmEnable OBJECT-TYPE
			SYNTAX INTEGER
				{
				disable(1),
				enable(2)
				}
			MAX-ACCESS read-write
			STATUS current
			DESCRIPTION 
				"This object indicates the status of the CRC error alarm function. The default value is 1."
			::= { hwAPPortLinkProfileEntry 4 }

		 --1.3.6.1.4.1.2011.6.139.11.1.15.1.5
		hwAPPortLinkProfileCrcAlarmThreshold OBJECT-TYPE
			SYNTAX Unsigned32 (1..100)
			MAX-ACCESS read-write
			STATUS current
			DESCRIPTION 
				"This object indicates a CRC error alarm threshold. The default value is 50. It is expressed in percentage."
			::= { hwAPPortLinkProfileEntry 5 }

		 --1.3.6.1.4.1.2011.6.139.11.1.15.1.6
		hwAPPortLinkProfileCrcAlarmResumeThreshold OBJECT-TYPE
			SYNTAX Unsigned32 (1..100)
			MAX-ACCESS read-write
			STATUS current
			DESCRIPTION 
				"This object indicates a CRC error alarm clearing threshold. The default value is 20. It is expressed in percentage."
			::= { hwAPPortLinkProfileEntry 6 }

		 --1.3.6.1.4.1.2011.6.139.11.1.15.1.7
		hwAPPortLinkProfileRowStatus OBJECT-TYPE
			SYNTAX RowStatus
			MAX-ACCESS read-create
			STATUS current
			DESCRIPTION 
				"This object indicates the row status of this table. ROWSTATUS_CREATEANDFLOW and ROWSTATUS_DESTROY are commonly used ?	ROWSTATUS_UNDEFINED: undefined ?	ROWSTATUS_ACTIVE: active ?	ROWSTATUS_NOTINSERVICE:notInService ?	ROWSTATUS_NOTREADY: notReady ?	ROWSTATUS_CREATEANDFLOW: createAndGo ?	ROWSTATUS_CREATEANDWAIT: createAndWait ?	ROWSTATUS_DESTROY: destroy."
			::= { hwAPPortLinkProfileEntry 7 }


 		 -- 1.3.6.1.4.1.2011.6.139.11.1.15.1.8
		hwAPPortLinkProfilePoeSwitch OBJECT-TYPE
			SYNTAX INTEGER
				{
				disable(1),
				enable(2)
				}
			MAX-ACCESS read-write
			STATUS current
			DESCRIPTION
				"This object indicates whether to enable the PoE function on the interface.The default value is 2."
			::= { hwAPPortLinkProfileEntry 8 }

		
		 -- 1.3.6.1.4.1.2011.6.139.11.1.15.1.9
		hwAPPortLinkProfilePoePriority OBJECT-TYPE
			SYNTAX INTEGER
				{
				critical(1),
				high(2),
				low(3)     
				}
			MAX-ACCESS read-write
			STATUS current
			DESCRIPTION
				"This object indicates the power priority of PoE interfaces.The default value is 3."
			::= { hwAPPortLinkProfileEntry 9 }

		
		 -- 1.3.6.1.4.1.2011.6.139.11.1.15.1.10
		hwAPPortLinkProfilePoeForcePowerSwitch OBJECT-TYPE
			SYNTAX INTEGER
				{
				disable(1),
				enable(2)
				}
			MAX-ACCESS read-write
			STATUS current
			DESCRIPTION
				"This object indicates whether to enable forcible PoE power supply on an interface.The default value is 1."
			::= { hwAPPortLinkProfileEntry 10 }

		
		 -- 1.3.6.1.4.1.2011.6.139.11.1.15.1.11
		hwAPPortLinkProfilePoeLegacySwitch OBJECT-TYPE
			SYNTAX INTEGER
				{
				disable(1),
				enable(2)
				}
			MAX-ACCESS read-write
			STATUS current
			DESCRIPTION
				"This object indicates whether to enable the PSE to check compatibility of the connected PDs.The default value is 1."
			::= { hwAPPortLinkProfileEntry 11 }

		
		 -- 1.3.6.1.4.1.2011.6.139.11.1.15.1.12
		hwAPPortLinkProfilePoeOffTimeRange OBJECT-TYPE
			SYNTAX OCTET STRING (SIZE (0..32))
			MAX-ACCESS read-write
			STATUS current
			DESCRIPTION
				"This object indicates whether to make a configured PoE power-off time range effective on interfaces."
			::= { hwAPPortLinkProfileEntry 12 }

			
		-- 1.3.6.1.4.1.2011.6.139.11.1.15.1.13
		hwAPPortLinkProfileAdminStatus OBJECT-TYPE
			SYNTAX INTEGER
				{
				down(1),
				up(2)
				}
			MAX-ACCESS read-write
			STATUS current
			DESCRIPTION
				"This object indicates whether to enable port shutdown.The default value is 2."
			::= { hwAPPortLinkProfileEntry 13 }
			
		--1.3.6.1.4.1.2011.6.139.11.1.16
		hw2gRadioProfileTable OBJECT-TYPE
			SYNTAX SEQUENCE OF Hw2gRadioProfileEntry 
			MAX-ACCESS not-accessible
			STATUS current
			DESCRIPTION 
				"This table is used to configure 2.4 GHz radio parameters, including physical radio parameters such as channel, power, antenna gain, and working mode, and bind air scan and RRM profiles."
			::= { hwWlanConfigObjects 16 }

		--1.3.6.1.4.1.2011.6.139.11.1.16.1
		hw2gRadioProfileEntry OBJECT-TYPE
			SYNTAX Hw2gRadioProfileEntry 
			MAX-ACCESS not-accessible
			STATUS current
			DESCRIPTION 
				"The index of this table is hw2gRadioProfileName."
			INDEX { hw2gRadioProfileName }
			::= { hw2gRadioProfileTable 1 }


		Hw2gRadioProfileEntry ::=
			SEQUENCE {				
				hw2gRadioProfileName
					OCTET STRING,
				hw2gRadioBeaconInterval
					Unsigned32,
				hw2gRadioGuardIntervalMode
					INTEGER,
				hw2gRadioShortPreamble
					INTEGER,
				hw2gRadioFragmentationThreshold
					Integer32,
				hw2gRadioHtAmpduSwitch
					INTEGER,
				hw2gRadioHtAmpduMaxLengthExponent
					Integer32,
				hw2gRadioDot11bgBasicRate
					Unsigned32,
				hw2gRadioDot11bgSupportRate
					Unsigned32,
				hw2gRadioMulticastRate
					Unsigned32,
				hw2gRadioWmmMandatorySwitch
					INTEGER,
				hw2gRadioApEDCAVoiceECWmax
					Unsigned32,
				hw2gRadioApEDCAVoiceECWmin
					Unsigned32,
				hw2gRadioApEDCAVoiceAIFSN
					Unsigned32,
				hw2gRadioApEDCAVoiceTXOPLimit
					Unsigned32,
				hw2gRadioApEDCAVoiceAckPolicy
					INTEGER,
				hw2gRadioApEDCAVideoECWmax
					Unsigned32,
				hw2gRadioApEDCAVideoECWmin
					Unsigned32,
				hw2gRadioApEDCAVideoAIFSN
					Unsigned32,
				hw2gRadioApEDCAVideoTXOPLimit
					Unsigned32,
				hw2gRadioApEDCAVideoAckPolicy
					INTEGER,
				hw2gRadioApEDCABEECWmax
					Unsigned32,
				hw2gRadioApEDCABEECWmin
					Unsigned32,
				hw2gRadioApEDCABEAIFSN
					Unsigned32,
				hw2gRadioApEDCABETXOPLimit
					Unsigned32,
				hw2gRadioApEDCABEAckPolicy
					INTEGER,
				hw2gRadioApEDCABKECWmax
					Unsigned32,
				hw2gRadioApEDCABKECWmin
					Unsigned32,
				hw2gRadioApEDCABKAIFSN
					Unsigned32,
				hw2gRadioApEDCABKTXOPLimit
					Unsigned32,
				hw2gRadioApEDCABKAckPolicy
					INTEGER,
				hw2gRadioWmmSwitch
					INTEGER,
				hw2gRadioRtsCtsThreshold
					Unsigned32,
				hw2gRadioRtsCtsMode
					INTEGER,
				hw2gRadioPowerAutoAdjustSwitch
					INTEGER,
				hw2gRadioBeamformingSwitch
					INTEGER,
				hw2gRadioWifiLight
					INTEGER,
				hw2gRadioChannelSwitchAnnouncementSwitch
					INTEGER,
				hw2gRadioChannelSwitchMode
					INTEGER,
				hw2gRadioAutoOffServiceSwitch
					INTEGER,
				hw2gRadioAutoOffServiceStartTime
					OCTET STRING,
				hw2gRadioAutoOffServiceEndTime
					OCTET STRING,
				hw2gRadioInterferenceDetectSwitch
					INTEGER,
				hw2gRadioInterferenceIntraFrequencyThreshold
					Unsigned32,
				hw2gRadioInterferenceAdjacentFrequencyThreshold
					Unsigned32,
				hw2gRadioInterferenceStationThreshold
					Unsigned32,
				hw2gRadioRrmProfile
					OCTET STRING,
				hw2gRadioAirScanProfile
					OCTET STRING,
				hw2gRadioProfileRowStatus
					RowStatus,
				hw2gRadioProfileUtmostPowerSwitch
					INTEGER,
				hw2gRadioProfileRadioType
					INTEGER,
				hw2gRadioProfileSmartAntennaEnable
					INTEGER,
				hw2gRadioProfileTxChainNum
					Unsigned32,
				hw2gRadioProfileRxChainNum
					Unsigned32
			 }

		 --1.3.6.1.4.1.2011.6.139.11.1.16.1.1
		hw2gRadioProfileName OBJECT-TYPE
			SYNTAX OCTET STRING (SIZE (1..35))
			MAX-ACCESS not-accessible
			STATUS current
			DESCRIPTION 
				"This object indicates the name of a 2G radio profile. It is the index of the table."
			::= { hw2gRadioProfileEntry 1 }

		
		-- 1.3.6.1.4.1.2011.6.139.11.1.16.1.6
		hw2gRadioBeaconInterval OBJECT-TYPE
			SYNTAX Unsigned32 (60..1000)
			MAX-ACCESS read-write
			STATUS current
			DESCRIPTION 
				"This object indicates a Beacon interval. The default value is 100. It is expressed in ms."
			::= { hw2gRadioProfileEntry 6 }

		
		-- 1.3.6.1.4.1.2011.6.139.11.1.16.1.10
		hw2gRadioGuardIntervalMode OBJECT-TYPE
			SYNTAX INTEGER
				{
				short(1),
				normal(2)
				}
			MAX-ACCESS read-write
			STATUS current
			DESCRIPTION 
				"This object indicates the GI mode. The default value is 2."
			::= { hw2gRadioProfileEntry 10 }

		 --1.3.6.1.4.1.2011.6.139.11.1.16.1.11
		hw2gRadioShortPreamble OBJECT-TYPE
			SYNTAX INTEGER
				{
				disable(1),
				enable(2)
				}
			MAX-ACCESS read-write
			STATUS current
			DESCRIPTION 
				"This object indicates the preamble mode. The default value is 2."
			::= { hw2gRadioProfileEntry 11 }

		 --1.3.6.1.4.1.2011.6.139.11.1.16.1.12
		hw2gRadioFragmentationThreshold OBJECT-TYPE
			SYNTAX Integer32 (256..2346)
			MAX-ACCESS read-write
			STATUS current
			DESCRIPTION 
				"This object indicates the packet fragmentation threshold. The default value is 2346. It is expressed in bytes."
			::= { hw2gRadioProfileEntry 12 }

		 --1.3.6.1.4.1.2011.6.139.11.1.16.1.13
		hw2gRadioHtAmpduSwitch OBJECT-TYPE
			SYNTAX INTEGER
				{
				disable(1) ,
				enable(2)
				}
			MAX-ACCESS read-write
			STATUS current
			DESCRIPTION 
				"This object indicates the status of the aggregation function. The default value is 2."
			::= { hw2gRadioProfileEntry 13 }

		 --1.3.6.1.4.1.2011.6.139.11.1.16.1.14
		hw2gRadioHtAmpduMaxLengthExponent OBJECT-TYPE
			SYNTAX Integer32 (0..3)
			MAX-ACCESS read-write
			STATUS current
			DESCRIPTION 
				"This object indicates the maximum length of frames converged by an MPDU. The default value is 3 ?	0: 8191 bytes ?	1: 16383 bytes ?	2: 32767 bytes ?	3: 65535 bytes."
			::= { hw2gRadioProfileEntry 14 }

		 --1.3.6.1.4.1.2011.6.139.11.1.16.1.15
		hw2gRadioDot11bgBasicRate OBJECT-TYPE
			SYNTAX Unsigned32 (1..4095)
			MAX-ACCESS read-write
			STATUS current
			DESCRIPTION 
				"This object indicates the basic rate set of the 802.11bg protocol. The default value is 3 ?	bit0: 1 Mbit/s ?	bit1: 2 Mbit/s ?	bit2: 5.5 Mbit/s ?	bit3: 6 Mbit/s ?	bit4: 9 Mbit/s ?	bit5: 11 Mbit/s ?	bit6: 12 Mbit/s ?	bit7: 18 Mbit/s ?	bit8: 24 Mbit/s ?	bit9: 36 Mbit/s ?	bit10: 48 Mbit/s ?	bit11: 54 Mbit/s."
			::= { hw2gRadioProfileEntry 15 }

		 --1.3.6.1.4.1.2011.6.139.11.1.16.1.16
		hw2gRadioDot11bgSupportRate OBJECT-TYPE
			SYNTAX Unsigned32 (1..4095)
			MAX-ACCESS read-write
			STATUS current
			DESCRIPTION 
				"This object indicates the supported rate set of the 802.11bg protocol. The default value is 0xFFF ?	bit0: 1 Mbit/s?	bit1: 2 Mbit/s?	bit2: 5.5 Mbit/s?	bit3: 6 Mbit/s?	bit4: 9 Mbit/s?	bit5: 11 Mbit/s?	bit6: 12 Mbit/s ?	bit7: 18 Mbit/s?	bit8: 24 Mbit/s?	bit9: 36 Mbit/s?	bit10: 48 Mbit/s?	bit11: 54 Mbit/s."
			::= { hw2gRadioProfileEntry 16 }

		 --1.3.6.1.4.1.2011.6.139.11.1.16.1.17
		hw2gRadioMulticastRate OBJECT-TYPE
			SYNTAX Unsigned32
			MAX-ACCESS read-write
			STATUS current
			DESCRIPTION 
				"This object indicates the multicast rate. The default value is 0x2F ?	bit0: 1 Mbit/s ?	bit1: 2 Mbit/s ?	bit2: 5.5 Mbit/s ?	bit3: 6 Mbit/s ?	bit4: 9 Mbit/s ?	bit5: 11 Mbit/s ?	bit6: 12 Mbit/s ?	bit7: 18 Mbit/s ?	bit8: 24 Mbit/s ?	bit9: 36 Mbit/s ?	bit10: 48 Mbit/s ?	bit11: 54 Mbit/s."
			::= { hw2gRadioProfileEntry 17 }

		 --1.3.6.1.4.1.2011.6.139.11.1.16.1.18
		hw2gRadioWmmMandatorySwitch OBJECT-TYPE
			SYNTAX INTEGER
				{
				disable(1) ,
				enable(2)
				}
			MAX-ACCESS read-write
			STATUS current
			DESCRIPTION 
				"This object indicates the status of the mandatory WMM matching function. The default value is 1."
			::= { hw2gRadioProfileEntry 18 }

		 --1.3.6.1.4.1.2011.6.139.11.1.16.1.19
		hw2gRadioApEDCAVoiceECWmax OBJECT-TYPE
			SYNTAX Unsigned32 (0..15)
			MAX-ACCESS read-write
			STATUS current
			DESCRIPTION 
				"This object indicates the EDCA parameter ECWmax, namely, exponent form of Cwmax, for voice services on APs. ECWmin and ECWmax determine the average backoff time (ECWmax > ECWmin). The default value is 3."
			::= { hw2gRadioProfileEntry 19 }

		 --1.3.6.1.4.1.2011.6.139.11.1.16.1.20
		hw2gRadioApEDCAVoiceECWmin OBJECT-TYPE
			SYNTAX Unsigned32 (0..15)
			MAX-ACCESS read-write
			STATUS current
			DESCRIPTION 
				"This object indicates the EDCA parameter ECWmin, namely, exponent form of Cwmin, for voice services on APs. ECWmin and ECWmax determine the average backoff time (ECWmax > ECWmin). The default value is 2."
			::= { hw2gRadioProfileEntry 20 }

		 --1.3.6.1.4.1.2011.6.139.11.1.16.1.21
		hw2gRadioApEDCAVoiceAIFSN OBJECT-TYPE
			SYNTAX Unsigned32 (1..15)
			MAX-ACCESS read-write
			STATUS current
			DESCRIPTION 
				"This object indicates the EDCA parameter AIFSN, namely, arbitration interframe spacing number, for voice services on APs. The default value is 1."
			::= { hw2gRadioProfileEntry 21 }

		 --1.3.6.1.4.1.2011.6.139.11.1.16.1.22
		hw2gRadioApEDCAVoiceTXOPLimit OBJECT-TYPE
			SYNTAX Unsigned32 (0..255)
			MAX-ACCESS read-write
			STATUS current
			DESCRIPTION 
				"This object indicates the EDCA parameter TXOPLimit, namely, transmission opportunity limit, for voice services on APs. The default value is 47. The unit is 32 us."
			::= { hw2gRadioProfileEntry 22 }

		 --1.3.6.1.4.1.2011.6.139.11.1.16.1.23
		hw2gRadioApEDCAVoiceAckPolicy OBJECT-TYPE
			SYNTAX INTEGER
				{
				normal(1),
				noAck(2)
				}
			MAX-ACCESS read-write
			STATUS current
			DESCRIPTION 
				"This object indicates the EDCA parameter AckPolicy for voice services on APs. The default value is 1."
			::= { hw2gRadioProfileEntry 23 }

		 --1.3.6.1.4.1.2011.6.139.11.1.16.1.24
		hw2gRadioApEDCAVideoECWmax OBJECT-TYPE
			SYNTAX Unsigned32 (0..15)
			MAX-ACCESS read-write
			STATUS current
			DESCRIPTION 
				"This object indicates the EDCA parameter ECWmax, namely, exponent form of Cwmax, for video services on APs. ECWmin and ECWmax determine the average backoff time (ECWmax > ECWmin). The default value is 4."
			::= { hw2gRadioProfileEntry 24 }

		 --1.3.6.1.4.1.2011.6.139.11.1.16.1.25
		hw2gRadioApEDCAVideoECWmin OBJECT-TYPE
			SYNTAX Unsigned32 (0..15)
			MAX-ACCESS read-write
			STATUS current
			DESCRIPTION 
				"This object indicates the EDCA parameter ECWmin, namely, exponent form of Cwmin, for video services on APs. ECWmin and ECWmax determine the average backoff time (ECWmax > ECWmin). The default value is 3."
			::= { hw2gRadioProfileEntry 25 }

		 --1.3.6.1.4.1.2011.6.139.11.1.16.1.26
		hw2gRadioApEDCAVideoAIFSN OBJECT-TYPE
			SYNTAX Unsigned32 (1..15)
			MAX-ACCESS read-write
			STATUS current
			DESCRIPTION 
				"This object indicates the EDCA parameter AIFSN, namely, arbitration interframe spacing number, for video services on APs. The default value is 1."
			::= { hw2gRadioProfileEntry 26 }

		 --1.3.6.1.4.1.2011.6.139.11.1.16.1.27
		hw2gRadioApEDCAVideoTXOPLimit OBJECT-TYPE
			SYNTAX Unsigned32 (0..255)
			MAX-ACCESS read-write
			STATUS current
			DESCRIPTION 
				"This object indicates the EDCA parameter TXOPLimit, namely, transmission opportunity limit, for video services on APs. The default value is 94. The unit is 32 us."
			::= { hw2gRadioProfileEntry 27 }

		 --1.3.6.1.4.1.2011.6.139.11.1.16.1.28
		hw2gRadioApEDCAVideoAckPolicy OBJECT-TYPE
			SYNTAX INTEGER
				{
				normal(1),
				noAck(2)
				}
			MAX-ACCESS read-write
			STATUS current
			DESCRIPTION 
				"This object indicates the EDCA parameter AckPolicy for video services on APs. The default value is 1."
			::= { hw2gRadioProfileEntry 28 }

		 --1.3.6.1.4.1.2011.6.139.11.1.16.1.29
		hw2gRadioApEDCABEECWmax OBJECT-TYPE
			SYNTAX Unsigned32 (0..15)
			MAX-ACCESS read-write
			STATUS current
			DESCRIPTION 
				"This object indicates the EDCA parameter ECWmax, namely, exponent form of Cwmax, for BE services on APs. ECWmin and ECWmax determine the average backoff time (ECWmax > ECWmin). The default value is 6."
			::= { hw2gRadioProfileEntry 29 }

		 --1.3.6.1.4.1.2011.6.139.11.1.16.1.30
		hw2gRadioApEDCABEECWmin OBJECT-TYPE
			SYNTAX Unsigned32 (0..15)
			MAX-ACCESS read-write
			STATUS current
			DESCRIPTION 
				"This object indicates the EDCA parameter ECWmin, namely, exponent form of Cwmin, for BE services on APs. ECWmin and ECWmax determine the average backoff time (ECWmax > ECWmin). The default value is 4."
			::= { hw2gRadioProfileEntry 30 }

		 --1.3.6.1.4.1.2011.6.139.11.1.16.1.31
		hw2gRadioApEDCABEAIFSN OBJECT-TYPE
			SYNTAX Unsigned32 (1..15)
			MAX-ACCESS read-write
			STATUS current
			DESCRIPTION 
				"This object indicates the EDCA parameter AIFSN, namely, arbitration interframe spacing number, for BE services on APs. The default value is 3."
			::= { hw2gRadioProfileEntry 31 }

		 --1.3.6.1.4.1.2011.6.139.11.1.16.1.32
		hw2gRadioApEDCABETXOPLimit OBJECT-TYPE
			SYNTAX Unsigned32 (0..255)
			MAX-ACCESS read-write
			STATUS current
			DESCRIPTION 
				"This object indicates the EDCA parameter TXOPLimit for BE services on APs. It indicates the transmission opportunity limit. The default value is 0. The unit is 32 us."
			::= { hw2gRadioProfileEntry 32 }

		 --1.3.6.1.4.1.2011.6.139.11.1.16.1.33
		hw2gRadioApEDCABEAckPolicy OBJECT-TYPE
			SYNTAX INTEGER
				{
				normal(1),
				noAck(2)
				}
			MAX-ACCESS read-write
			STATUS current
			DESCRIPTION 
				"This object indicates the EDCA parameter AckPolicy for BE services on APs. The default value is 1."
			::= { hw2gRadioProfileEntry 33 }

		 --1.3.6.1.4.1.2011.6.139.11.1.16.1.34
		hw2gRadioApEDCABKECWmax OBJECT-TYPE
			SYNTAX Unsigned32 (0..15)
			MAX-ACCESS read-write
			STATUS current
			DESCRIPTION 
				"This object indicates the EDCA parameter ECWmax, namely, exponent form of Cwmax, for BK services on APs. ECWmin and ECWmax determine the average backoff time (ECWmax > ECWmin). The default value is 10."
			::= { hw2gRadioProfileEntry 34 }

		 --1.3.6.1.4.1.2011.6.139.11.1.16.1.35
		hw2gRadioApEDCABKECWmin OBJECT-TYPE
			SYNTAX Unsigned32 (0..15)
			MAX-ACCESS read-write
			STATUS current
			DESCRIPTION 
				"This object indicates the EDCA parameter ECWmin, namely, exponent form of Cwmin, for BK services on APs. ECWmin and ECWmax determine the average backoff time (ECWmax > ECWmin). The default value is 4."
			::= { hw2gRadioProfileEntry 35 }

		 --1.3.6.1.4.1.2011.6.139.11.1.16.1.36
		hw2gRadioApEDCABKAIFSN OBJECT-TYPE
			SYNTAX Unsigned32 (1..15)
			MAX-ACCESS read-write
			STATUS current
			DESCRIPTION 
				"This object indicates the EDCA parameter AIFSN, namely, arbitration interframe spacing number, for BK services on APs. The default value is 7."
			::= { hw2gRadioProfileEntry 36 }

		 --1.3.6.1.4.1.2011.6.139.11.1.16.1.37
		hw2gRadioApEDCABKTXOPLimit OBJECT-TYPE
			SYNTAX Unsigned32 (0..255)
			MAX-ACCESS read-write
			STATUS current
			DESCRIPTION 
				"This object indicates the EDCA parameter TXOPLimit, namely, transmission opportunity limit, for BK services on APs. The default value is 0. The unit is 32 us."
			::= { hw2gRadioProfileEntry 37 }

		 --1.3.6.1.4.1.2011.6.139.11.1.16.1.38
		hw2gRadioApEDCABKAckPolicy OBJECT-TYPE
			SYNTAX INTEGER
				{
				normal(1),
				noAck(2)
				}
			MAX-ACCESS read-write
			STATUS current
			DESCRIPTION 
				"This object indicates the EDCA parameter AckPolicy for BK services on APs. The default value is 1."
			::= { hw2gRadioProfileEntry 38 }

		 --1.3.6.1.4.1.2011.6.139.11.1.16.1.39
		hw2gRadioWmmSwitch OBJECT-TYPE
			SYNTAX INTEGER
				{
				disable(1) ,
				enable(2)
				}
			MAX-ACCESS read-write
			STATUS current
			DESCRIPTION 
				"This object indicates the status of the WMM function. The default value is 2."
			::= { hw2gRadioProfileEntry 39 }

		 --1.3.6.1.4.1.2011.6.139.11.1.16.1.40
		hw2gRadioRtsCtsThreshold OBJECT-TYPE
			SYNTAX Unsigned32 (64..2347)
			MAX-ACCESS read-write
			STATUS current
			DESCRIPTION 
				"This object indicates the request To Send/Clear To Send (RTS/CTS) threshold. If the length of a frame to be sent by the MAC Layer exceeds this threshold, an RTS frame needs to be sent before this frame. The default value is 2347. It is expressed in bytes."
			::= { hw2gRadioProfileEntry 40 }

		 --1.3.6.1.4.1.2011.6.139.11.1.16.1.41
		hw2gRadioRtsCtsMode OBJECT-TYPE
			SYNTAX INTEGER
				{
				disable(1) ,
				ctsToSelf(2)  ,
				rtsCts(3)
				}
			MAX-ACCESS read-write
			STATUS current
			DESCRIPTION 
				"This object indicates the RTS-CTS mode set for the specified radio profile. The default value is 2."
			::= { hw2gRadioProfileEntry 41 }

		 --1.3.6.1.4.1.2011.6.139.11.1.16.1.42
		hw2gRadioPowerAutoAdjustSwitch OBJECT-TYPE
			SYNTAX INTEGER
				{
				disable(1) ,
				enable(2)
				}
			MAX-ACCESS read-write
			STATUS current
			DESCRIPTION 
				"This object indicates the status of the user-by-user power control function. The default value is 1."
			::= { hw2gRadioProfileEntry 42 }

		 --1.3.6.1.4.1.2011.6.139.11.1.16.1.43
		hw2gRadioBeamformingSwitch OBJECT-TYPE
			SYNTAX INTEGER
				{
				disable(1) ,
				enable(2)
				}
			MAX-ACCESS read-write
			STATUS current
			DESCRIPTION 
				"This object indicates the status of the beamforming function. The default value is 1."
			::= { hw2gRadioProfileEntry 43 }

		 --1.3.6.1.4.1.2011.6.139.11.1.16.1.44
		hw2gRadioWifiLight OBJECT-TYPE
			SYNTAX INTEGER
				{
				signalStrength(1) ,
				traffic(2)
				}
			MAX-ACCESS read-write
			STATUS current
			DESCRIPTION 
				"This object indicates information reflected by the blinking frequency of the Wireless LED on an AP."
			::= { hw2gRadioProfileEntry 44 }

		 --1.3.6.1.4.1.2011.6.139.11.1.16.1.45
		hw2gRadioChannelSwitchAnnouncementSwitch OBJECT-TYPE
			SYNTAX INTEGER
				{
				disable(1) ,
				enable(2)
				}
			MAX-ACCESS read-write
			STATUS current
			DESCRIPTION 
				"This object indicates the status of the channel switchover announcement function. The default value is 1."
			::= { hw2gRadioProfileEntry 45 }

		 --1.3.6.1.4.1.2011.6.139.11.1.16.1.46
		hw2gRadioChannelSwitchMode OBJECT-TYPE
			SYNTAX INTEGER
				{
				continueTransmitting(1) ,
				stopTransmitting(2)
				}
			MAX-ACCESS read-write
			STATUS current
			DESCRIPTION 
				"This object indicates the channel switch announcement mode. The default value is 1."
			::= { hw2gRadioProfileEntry 46 }

		 --1.3.6.1.4.1.2011.6.139.11.1.16.1.47
		hw2gRadioAutoOffServiceSwitch OBJECT-TYPE
			SYNTAX INTEGER
				{
				disable(1) ,
				enable(2)
				}
			MAX-ACCESS read-write
			STATUS current
			DESCRIPTION 
				"This object indicates the status of the scheduled radio disabling function. The default value is 1."
			::= { hw2gRadioProfileEntry 47 }

		 --1.3.6.1.4.1.2011.6.139.11.1.16.1.48
		hw2gRadioAutoOffServiceStartTime OBJECT-TYPE
			SYNTAX OCTET STRING (SIZE (1..11))
			MAX-ACCESS read-write
			STATUS current
			DESCRIPTION 
				"This object indicates the start time for disabling the radio. The value is in the format of hh:mm:ss NOTE ?	hh specifies the hour. The value is an integer that ranges from 0 to 23.?	mm specifies the minute. The value is an integer that ranges from 0 to 59.?	ss specifies the second. The value is an integer that ranges from 0 to 59."
			::= { hw2gRadioProfileEntry 48 }

		 --1.3.6.1.4.1.2011.6.139.11.1.16.1.49
		hw2gRadioAutoOffServiceEndTime OBJECT-TYPE
			SYNTAX OCTET STRING (SIZE (1..11))
			MAX-ACCESS read-write
			STATUS current
			DESCRIPTION 
				"This object indicates the end time for disabling of the radio. The value is in the format of hh:mm:ss NOTE ?	hh specifies the hour. The value is an integer that ranges from 0 to 23.?	mm specifies the minute. The value is an integer that ranges from 0 to 59.?	ss specifies the second. The value is an integer that ranges from 0 to 59."
			::= { hw2gRadioProfileEntry 49 }

		 --1.3.6.1.4.1.2011.6.139.11.1.16.1.50
		hw2gRadioInterferenceDetectSwitch OBJECT-TYPE
			SYNTAX INTEGER
				{
				disable(1) ,
				enable(2)
				}
			MAX-ACCESS read-write
			STATUS current
			DESCRIPTION 
				"This object indicates the status of the user-by-user power control function. The default value is 1."
			::= { hw2gRadioProfileEntry 50 }

		 --1.3.6.1.4.1.2011.6.139.11.1.16.1.51
		hw2gRadioInterferenceIntraFrequencyThreshold OBJECT-TYPE
			SYNTAX Unsigned32 (1..100)
			MAX-ACCESS read-write
			STATUS current
			DESCRIPTION 
				"This object indicates the alarm threshold for co-channel interference, namely, the percentage of the co-channel interference power against the maximum power. The default value is 50."
			::= { hw2gRadioProfileEntry 51 }

		 --1.3.6.1.4.1.2011.6.139.11.1.16.1.52
		hw2gRadioInterferenceAdjacentFrequencyThreshold OBJECT-TYPE
			SYNTAX Unsigned32 (1..100)
			MAX-ACCESS read-write
			STATUS current
			DESCRIPTION 
				"This object indicates the alarm threshold for adjacent-channel interference, namely, the percentage of the adjacent-channel interference power against the maximum power. The default value is 50."
			::= { hw2gRadioProfileEntry 52 }

		 --1.3.6.1.4.1.2011.6.139.11.1.16.1.53
		hw2gRadioInterferenceStationThreshold OBJECT-TYPE
			SYNTAX Unsigned32 (1..256)
			MAX-ACCESS read-write
			STATUS current
			DESCRIPTION 
				"This object indicates the alarm threshold for station interference. When the number of the STAs detected exceeds the specified alarm threshold, the AP reports alarms to the AC.The default value is 32."
			::= { hw2gRadioProfileEntry 53 }

		 --1.3.6.1.4.1.2011.6.139.11.1.16.1.54
		hw2gRadioRrmProfile OBJECT-TYPE
			SYNTAX OCTET STRING (SIZE (1..35))
			MAX-ACCESS read-write
			STATUS current
			DESCRIPTION 
				"This object indicates the bound RRM profile."
			::= { hw2gRadioProfileEntry 54 }

		 --1.3.6.1.4.1.2011.6.139.11.1.16.1.55
		hw2gRadioAirScanProfile OBJECT-TYPE
			SYNTAX OCTET STRING (SIZE (1..35))
			MAX-ACCESS read-write
			STATUS current
			DESCRIPTION 
				"This object indicates the bound air scan profile."
			::= { hw2gRadioProfileEntry 55 }

		 --1.3.6.1.4.1.2011.6.139.11.1.16.1.56
		hw2gRadioProfileRowStatus OBJECT-TYPE
			SYNTAX RowStatus
			MAX-ACCESS read-write
			STATUS current
			DESCRIPTION 
				"This object indicates the row status of this table. ROWSTATUS_CREATEANDFLOW and ROWSTATUS_DESTROY are commonly used ?	ROWSTATUS_UNDEFINED: undefined?	ROWSTATUS_ACTIVE: active?	ROWSTATUS_NOTINSERVICE: notInService?	ROWSTATUS_NOTREADY: notReady?	ROWSTATUS_CREATEANDFLOW: createAndGo?	ROWSTATUS_CREATEANDWAIT: createAndWait?	ROWSTATUS_DESTROY: destroy."
			::= { hw2gRadioProfileEntry 56 }

		-- 1.3.6.1.4.1.2011.6.139.11.1.16.1.57
		hw2gRadioProfileUtmostPowerSwitch OBJECT-TYPE
			SYNTAX INTEGER
				{
				disable(1),
				enable(2)
				}
			MAX-ACCESS read-write
			STATUS current
			DESCRIPTION
				"This object indicates the switch for the function of sending packets at maximum power."
			::= { hw2gRadioProfileEntry 57 }

		-- 1.3.6.1.4.1.2011.6.139.11.1.16.1.59
		hw2gRadioProfileRadioType OBJECT-TYPE
			SYNTAX INTEGER
				{
				dot11b(1),
				dot11g(5),
				dot11n(9)
				}
			MAX-ACCESS read-write
			STATUS current
			DESCRIPTION
				"This object indicates the type of radio. The default value is 9. "
			::= { hw2gRadioProfileEntry 59 }

		-- 1.3.6.1.4.1.2011.6.139.11.1.16.1.60
		hw2gRadioProfileSmartAntennaEnable OBJECT-TYPE
			SYNTAX INTEGER
				{
				disable(1),
				enable(2)
				}
			MAX-ACCESS read-write
			STATUS current
			DESCRIPTION
				"Description."
			DEFVAL { disable }
			::= { hw2gRadioProfileEntry 60 }

		-- 1.3.6.1.4.1.2011.6.139.11.1.16.1.61
		hw2gRadioProfileTxChainNum OBJECT-TYPE
			SYNTAX Unsigned32 (1..4)
			MAX-ACCESS read-write
			STATUS current
			DESCRIPTION
				"Description."
			DEFVAL { 4 }
			::= { hw2gRadioProfileEntry 61 }
		
		-- 1.3.6.1.4.1.2011.6.139.11.1.16.1.62
		hw2gRadioProfileRxChainNum OBJECT-TYPE
			SYNTAX Unsigned32 (1..4)
			MAX-ACCESS read-write
			STATUS current
			DESCRIPTION
				"Description."
			DEFVAL { 4 }
			::= { hw2gRadioProfileEntry 62 }		
		
		-- 1.3.6.1.4.1.2011.6.139.11.1.17
		hw5gRadioProfileTable OBJECT-TYPE
			SYNTAX SEQUENCE OF Hw5gRadioProfileEntry 
			MAX-ACCESS not-accessible
			STATUS current
			DESCRIPTION 
				"This table is used to configure 5 GHz radio parameters, including physical radio parameters such as channel, power, antenna gain, and working mode, and bind air scan profiles and RRM profiles."
			::= { hwWlanConfigObjects 17 }

		--1.3.6.1.4.1.2011.6.139.11.1.17.1
		hw5gRadioProfileEntry OBJECT-TYPE
			SYNTAX Hw5gRadioProfileEntry 
			MAX-ACCESS not-accessible
			STATUS current
			DESCRIPTION 
				"The index of this table is hw5gRadioProfileName."
			INDEX { hw5gRadioProfileName }
			::= { hw5gRadioProfileTable 1 }


		Hw5gRadioProfileEntry ::=
			SEQUENCE {				
				hw5gRadioProfileName
					OCTET STRING,
				hw5gRadioBeaconInterval
					Unsigned32,
				hw5gRadioGuardIntervalMode
					INTEGER,
				hw5gRadioShortPreamble
					INTEGER,
				hw5gRadioFragmentationThreshold
					Unsigned32,
				hw5gRadioHtAmpduSwitch
					INTEGER,
				hw5gRadioHtAmpduMaxLengthExponent
					Unsigned32,
				hw5gRadioVhtAmpduMaxLengthExponent
					Integer32,
				hw5gRadioVhtAmsduSwitch
					INTEGER,
				hw5gRadioVhtAmsduMaxFrameNum
					Unsigned32,
				hw5gRadioDot11aBasicRate
					Unsigned32,
				hw5gRadioDot11aSupportRate
					Unsigned32,
				hw5gRadioMulticastRate
					Unsigned32,
				hw5gRadioVhtNssMapMaxMcs
					OCTET STRING,
				hw5gRadioWmmMandatorySwitch
					INTEGER,
				hw5gRadioApEDCAVoiceECWmax
					Unsigned32,
				hw5gRadioApEDCAVoiceECWmin
					Unsigned32,
				hw5gRadioApEDCAVoiceAIFSN
					Unsigned32,
				hw5gRadioApEDCAVoiceTXOPLimit
					Unsigned32,
				hw5gRadioApEDCAVoiceAckPolicy
					INTEGER,
				hw5gRadioApEDCAVideoECWmax
					Unsigned32,
				hw5gRadioApEDCAVideoECWmin
					Unsigned32,
				hw5gRadioApEDCAVideoAIFSN
					Unsigned32,
				hw5gRadioApEDCAVideoTXOPLimit
					Unsigned32,
				hw5gRadioApEDCAVideoAckPolicy
					INTEGER,
				hw5gRadioApEDCABEECWmax
					Unsigned32,
				hw5gRadioApEDCABEECWmin
					Unsigned32,
				hw5gRadioApEDCABEAIFSN
					Unsigned32,
				hw5gRadioApEDCABETXOPLimit
					Unsigned32,
				hw5gRadioApEDCABEAckPolicy
					INTEGER,
				hw5gRadioApEDCABKECWmax
					Unsigned32,
				hw5gRadioApEDCABKECWmin
					Unsigned32,
				hw5gRadioApEDCABKAIFSN
					Unsigned32,
				hw5gRadioApEDCABKTXOPLimit
					Unsigned32,
				hw5gRadioApEDCABKAckPolicy
					INTEGER,
				hw5gRadioWmmSwitch
					INTEGER,
				hw5gRadioRtsCtsThreshold
					Unsigned32,
				hw5gRadioRtsCtsMode
					INTEGER,
				hw5gRadioPowerAutoAdjustSwitch
					INTEGER,
				hw5gRadioBeamformingSwitch
					INTEGER,
				hw5gRadioWifiLight
					INTEGER,
				hw5gRadioChannelSwitchAnnouncementSwitch
					INTEGER,
				hw5gRadioChannelSwitchMode
					INTEGER,
				hw5gRadioAutoOffServiceSwitch
					INTEGER,
				hw5gRadioAutoOffServiceStartTime
					OCTET STRING,
				hw5gRadioAutoOffServiceEndTime
					OCTET STRING,
				hw5gRadioInterferenceDetectSwitch
					INTEGER,
				hw5gRadioInterferenceIntraFrequencyThreshold
					Unsigned32,
				hw5gRadioInterferenceAdjacentFrequencyThreshold
					Unsigned32,
				hw5gRadioInterferenceStationThreshold
					Unsigned32,
				hw5gRadioRrmProfile
					OCTET STRING,
				hw5gRadioAirScanProfile
					OCTET STRING,
				hw5gRadioProfileRowStatus
					RowStatus,
				hw5gRadioProfileUtmostPowerSwitch
					INTEGER,
				hw5gRadioProfileRadioType
					INTEGER,
				hw5gRadioProfileSmartAntennaEnable
					INTEGER,
				hw5gRadioProfileMuMIMOEnable
					INTEGER,
				hw5gRadioProfileTxChainNum
					Unsigned32,
				hw5gRadioProfileRxChainNum
					Unsigned32
			 }

		 --1.3.6.1.4.1.2011.6.139.11.1.17.1.1
		hw5gRadioProfileName OBJECT-TYPE
			SYNTAX OCTET STRING (SIZE (1..35))
			MAX-ACCESS not-accessible
			STATUS current
			DESCRIPTION 
				"This object indicates the name of a 5G radio profile. It is the index of the table."
			::= { hw5gRadioProfileEntry 1 }

		
		-- 1.3.6.1.4.1.2011.6.139.11.1.17.1.6
		hw5gRadioBeaconInterval OBJECT-TYPE
			SYNTAX Unsigned32 (60..1000)
			MAX-ACCESS read-write
			STATUS current
			DESCRIPTION 
				"This object indicates a Beacon interval. The default value is 100. It is expressed in ms."
			::= { hw5gRadioProfileEntry 6 }

		
		-- 1.3.6.1.4.1.2011.6.139.11.1.17.1.10
		hw5gRadioGuardIntervalMode OBJECT-TYPE
			SYNTAX INTEGER
				{
				short(1),
				normal(2)
				}
			MAX-ACCESS read-write
			STATUS current
			DESCRIPTION 
				"This object indicates the GI mode. The default value is 2."
			::= { hw5gRadioProfileEntry 10 }

		 --1.3.6.1.4.1.2011.6.139.11.1.17.1.11
		hw5gRadioShortPreamble OBJECT-TYPE
			SYNTAX INTEGER
				{
				disable(1),
				enable(2)
				}
			MAX-ACCESS read-write
			STATUS current
			DESCRIPTION 
				"This object indicates whether the short preamble is enabled. The default value is 2."
			::= { hw5gRadioProfileEntry 11 }

		 --1.3.6.1.4.1.2011.6.139.11.1.17.1.12
		hw5gRadioFragmentationThreshold OBJECT-TYPE
			SYNTAX Unsigned32 (256..2346)
			MAX-ACCESS read-write
			STATUS current
			DESCRIPTION 
				"This object indicates the packet fragmentation threshold. The default value is 2346. It is expressed in bytes."
			::= { hw5gRadioProfileEntry 12 }

		 --1.3.6.1.4.1.2011.6.139.11.1.17.1.13
		hw5gRadioHtAmpduSwitch OBJECT-TYPE
			SYNTAX INTEGER
				{
				disable(1) ,
				enable(2)
				}
			MAX-ACCESS read-write
			STATUS current
			DESCRIPTION 
				"This object indicates the status of the aggregation function. The default value is 2."
			::= { hw5gRadioProfileEntry 13 }

		 --1.3.6.1.4.1.2011.6.139.11.1.17.1.14
		hw5gRadioHtAmpduMaxLengthExponent OBJECT-TYPE
			SYNTAX Unsigned32 (0..3)
			MAX-ACCESS read-write
			STATUS current
			DESCRIPTION 
				"This object indicates the maximum length of frames converged by an MPDU. The default value is 3 ?	0: 8191 bytes?	1: 16383 bytes?	2: 32767 bytes ?	3: 65535 bytes."
			::= { hw5gRadioProfileEntry 14 }

		 --1.3.6.1.4.1.2011.6.139.11.1.17.1.15
		hw5gRadioVhtAmpduMaxLengthExponent OBJECT-TYPE
			SYNTAX Integer32 (0..7)
			MAX-ACCESS read-write
			STATUS current
			DESCRIPTION 
				"This object indicates the maximum length of frames converged by an MPDU. The default value is 7 ?	0: 8191 bytes?	1: 16383 bytes?	2: 32767 bytes?	3: 65535 bytes?	4: 131071 bytes?	5: 262143 bytes?	6: 524287 bytes?	7: 1048575 bytes."
			::= { hw5gRadioProfileEntry 15 }

		 --1.3.6.1.4.1.2011.6.139.11.1.17.1.16
		hw5gRadioVhtAmsduSwitch OBJECT-TYPE
			SYNTAX INTEGER
				{
				disable(1),
				enable(2)
				}
			MAX-ACCESS read-write
			STATUS current
			DESCRIPTION 
				"This object indicates the status of the A-MSDU aggregation function. The default value is 1."
			::= { hw5gRadioProfileEntry 16 }

		 --1.3.6.1.4.1.2011.6.139.11.1.17.1.17
		hw5gRadioVhtAmsduMaxFrameNum OBJECT-TYPE
			SYNTAX Unsigned32 (2..15)
			MAX-ACCESS read-write
			STATUS current
			DESCRIPTION 
				"This object indicates the maximum number of sub-frames that can be aggregated into an A-MSDU. The default value is 2."
			::= { hw5gRadioProfileEntry 17 }

		 --1.3.6.1.4.1.2011.6.139.11.1.17.1.18
		hw5gRadioDot11aBasicRate OBJECT-TYPE
			SYNTAX Unsigned32 (1..4095)
			MAX-ACCESS read-write
			STATUS current
			DESCRIPTION 
				"This object indicates the basic rate set of the 802.11bg protocol. The default value is 0x148 (6 Mbit/s/12 Mbit/s/24 Mbit/s) ?	bit0: 1 Mbit/s?	bit1: 2 Mbit/s?	bit2: 5.5 Mbit/s?	bit3: 6 Mbit/s?	bit4: 9 Mbit/s?	bit5: 11 Mbit/s?	bit6: 12 Mbit/s?	bit7: 18 Mbit/s?	bit8: 24 Mbit/s?	bit9: 36 Mbit/s?	bit10: 48 Mbit/s?	bit11: 54 Mbit/s."
			::= { hw5gRadioProfileEntry 18 }

		 --1.3.6.1.4.1.2011.6.139.11.1.17.1.19
		hw5gRadioDot11aSupportRate OBJECT-TYPE
			SYNTAX Unsigned32 (1..4095)
			MAX-ACCESS read-write
			STATUS current
			DESCRIPTION 
				"This object indicates the supported rate set of the 802.11bg protocol. The default value is 0xFD8 (6 Mbit/s/9 Mbit/s/12 Mbit/s/18 Mbit/s/24 Mbit/s/36 Mbit/s/48 Mbit/s/54 Mbit/s).?	bit0: 1 Mbit/s?	bit1: 2 Mbit/s?	bit2: 5.5 Mbit/s?	bit3: 6 Mbit/s?	bit4: 9 Mbit/s?	bit5: 11 Mbit/s?	bit6: 12 Mbit/s?	bit7: 18 Mbit/s?	bit8: 24 Mbit/s?	bit9: 36 Mbit/s?	bit10: 48 Mbit/s?	bit11: 54 Mbit/s."
			::= { hw5gRadioProfileEntry 19 }

		 --1.3.6.1.4.1.2011.6.139.11.1.17.1.20
		hw5gRadioMulticastRate OBJECT-TYPE
			SYNTAX Unsigned32
			MAX-ACCESS read-write
			STATUS current
			DESCRIPTION 
				"This object indicates the multicast rate. The default value is 0x8(6M).?	bit0: 1 Mbit/s?	bit1: 2 Mbit/s?	bit2: 5.5 Mbit/s?	bit3: 6 Mbit/s?	bit4: 9 Mbit/s?	bit5: 11 Mbit/s?	bit6: 12 Mbit/s?	bit7: 18 Mbit/s?	bit8: 24 Mbit/s?	bit9: 36 Mbit/s?	bit10: 48 Mbit/s?	bit11: 54 Mbit/s."
			::= { hw5gRadioProfileEntry 20 }

		 --1.3.6.1.4.1.2011.6.139.11.1.17.1.21
		hw5gRadioVhtNssMapMaxMcs OBJECT-TYPE
			SYNTAX OCTET STRING (SIZE (0..255))
			MAX-ACCESS read-write
			STATUS current
			DESCRIPTION 
				"This object indicates the maximum MCS value for 802.11ac radios. The number of spatial flows is 3 and the maximum MCS value is 7-9. The format is x?x?x. The default value is 9?9?9.."
			::= { hw5gRadioProfileEntry 21 }

		 --1.3.6.1.4.1.2011.6.139.11.1.17.1.22
		hw5gRadioWmmMandatorySwitch OBJECT-TYPE
			SYNTAX INTEGER
				{
				disable(1) ,
				enable(2)
				}
			MAX-ACCESS read-write
			STATUS current
			DESCRIPTION 
				"This object indicates the status of the mandatory WMM matching function. The default value is 1."
			::= { hw5gRadioProfileEntry 22 }

		 --1.3.6.1.4.1.2011.6.139.11.1.17.1.23
		hw5gRadioApEDCAVoiceECWmax OBJECT-TYPE
			SYNTAX Unsigned32 (0..15)
			MAX-ACCESS read-write
			STATUS current
			DESCRIPTION 
				"This object indicates the EDCA parameter ECWmax, namely, exponent form of Cwmax, for voice services on APs. ECWmin and ECWmax determine the average backoff time (ECWmax > ECWmin). The default value is 3."
			::= { hw5gRadioProfileEntry 23 }

		 --1.3.6.1.4.1.2011.6.139.11.1.17.1.24
		hw5gRadioApEDCAVoiceECWmin OBJECT-TYPE
			SYNTAX Unsigned32 (0..15)
			MAX-ACCESS read-write
			STATUS current
			DESCRIPTION 
				"This object indicates the EDCA parameter ECWmin, namely, exponent form of Cwmin, for voice services on APs. ECWmin and ECWmax determine the average backoff time (ECWmax > ECWmin). The default value is 2."
			::= { hw5gRadioProfileEntry 24 }

		 --1.3.6.1.4.1.2011.6.139.11.1.17.1.25
		hw5gRadioApEDCAVoiceAIFSN OBJECT-TYPE
			SYNTAX Unsigned32 (1..15)
			MAX-ACCESS read-write
			STATUS current
			DESCRIPTION 
				"This object indicates the EDCA parameter AIFSN, namely, arbitration interframe spacing number, for voice services on APs. The default value is 1."
			::= { hw5gRadioProfileEntry 25 }

		 --1.3.6.1.4.1.2011.6.139.11.1.17.1.26
		hw5gRadioApEDCAVoiceTXOPLimit OBJECT-TYPE
			SYNTAX Unsigned32 (0..255)
			MAX-ACCESS read-write
			STATUS current
			DESCRIPTION 
				"This object indicates the EDCA parameter TXOPLimit, namely, transmission opportunity limit, for voice services on APs. The default value is 47. The unit is 32 us."
			::= { hw5gRadioProfileEntry 26 }

		 --1.3.6.1.4.1.2011.6.139.11.1.17.1.27
		hw5gRadioApEDCAVoiceAckPolicy OBJECT-TYPE
			SYNTAX INTEGER
				{
				normal(1),
				noAck(2)
				}
			MAX-ACCESS read-write
			STATUS current
			DESCRIPTION 
				"This object indicates the EDCA parameter AckPolicy for voice services on APs. The default value is 1."
			::= { hw5gRadioProfileEntry 27 }

		 --1.3.6.1.4.1.2011.6.139.11.1.17.1.28
		hw5gRadioApEDCAVideoECWmax OBJECT-TYPE
			SYNTAX Unsigned32 (0..15)
			MAX-ACCESS read-write
			STATUS current
			DESCRIPTION 
				"This object indicates the EDCA parameter ECWmax, namely, exponent form of Cwmax, for video services on APs. ECWmin and ECWmax determine the average backoff time (ECWmax > ECWmin). The default value is 4."
			::= { hw5gRadioProfileEntry 28 }

		 --1.3.6.1.4.1.2011.6.139.11.1.17.1.29
		hw5gRadioApEDCAVideoECWmin OBJECT-TYPE
			SYNTAX Unsigned32 (0..15)
			MAX-ACCESS read-write
			STATUS current
			DESCRIPTION 
				"This object indicates the EDCA parameter ECWmin, namely, exponent form of Cwmin, for video services on APs. ECWmin and ECWmax determine the average backoff time (ECWmax > ECWmin). The default value is 3."
			::= { hw5gRadioProfileEntry 29 }

		 --1.3.6.1.4.1.2011.6.139.11.1.17.1.30
		hw5gRadioApEDCAVideoAIFSN OBJECT-TYPE
			SYNTAX Unsigned32 (1..15)
			MAX-ACCESS read-write
			STATUS current
			DESCRIPTION 
				"This object indicates the EDCA parameter AIFSN, namely, arbitration interframe spacing number, for video services on APs. The default value is 1."
			::= { hw5gRadioProfileEntry 30 }

		 --1.3.6.1.4.1.2011.6.139.11.1.17.1.31
		hw5gRadioApEDCAVideoTXOPLimit OBJECT-TYPE
			SYNTAX Unsigned32 (0..255)
			MAX-ACCESS read-write
			STATUS current
			DESCRIPTION 
				"This object indicates the EDCA parameter TXOPLimit, namely, transmission opportunity limit, for video services on APs. The default value is 94. The unit is 32 us."
			::= { hw5gRadioProfileEntry 31 }

		 --1.3.6.1.4.1.2011.6.139.11.1.17.1.32
		hw5gRadioApEDCAVideoAckPolicy OBJECT-TYPE
			SYNTAX INTEGER
				{
				normal(1),
				noAck(2)
				}
			MAX-ACCESS read-write
			STATUS current
			DESCRIPTION 
				"This object indicates the EDCA parameter AckPolicy for video services on APs. The default value is 1."
			::= { hw5gRadioProfileEntry 32 }

		 --1.3.6.1.4.1.2011.6.139.11.1.17.1.33
		hw5gRadioApEDCABEECWmax OBJECT-TYPE
			SYNTAX Unsigned32 (0..15)
			MAX-ACCESS read-write
			STATUS current
			DESCRIPTION 
				"This object indicates the EDCA parameter ECWmax, namely, exponent form of Cwmax, for BE services on APs. ECWmin and ECWmax determine the average backoff time (ECWmax > ECWmin). The default value is 6."
			::= { hw5gRadioProfileEntry 33 }

		 --1.3.6.1.4.1.2011.6.139.11.1.17.1.34
		hw5gRadioApEDCABEECWmin OBJECT-TYPE
			SYNTAX Unsigned32 (0..15)
			MAX-ACCESS read-write
			STATUS current
			DESCRIPTION 
				"This object indicates the EDCA parameter ECWmin, namely, exponent form of Cwmin, for BE services on APs. ECWmin and ECWmax determine the average backoff time (ECWmax > ECWmin). The default value is 4."
			::= { hw5gRadioProfileEntry 34 }

		 --1.3.6.1.4.1.2011.6.139.11.1.17.1.35
		hw5gRadioApEDCABEAIFSN OBJECT-TYPE
			SYNTAX Unsigned32 (1..15)
			MAX-ACCESS read-write
			STATUS current
			DESCRIPTION 
				"This object indicates the EDCA parameter AIFSN, namely, arbitration interframe spacing number, for BE services on APs. The default value is 3."
			::= { hw5gRadioProfileEntry 35 }

		 --1.3.6.1.4.1.2011.6.139.11.1.17.1.36
		hw5gRadioApEDCABETXOPLimit OBJECT-TYPE
			SYNTAX Unsigned32 (0..255)
			MAX-ACCESS read-write
			STATUS current
			DESCRIPTION 
				"This object indicates the EDCA parameter TXOPLimit, namely, transmission opportunity limit, for BE services on APs. The default value is 0. The unit is 32 us."
			::= { hw5gRadioProfileEntry 36 }

		 --1.3.6.1.4.1.2011.6.139.11.1.17.1.37
		hw5gRadioApEDCABEAckPolicy OBJECT-TYPE
			SYNTAX INTEGER
				{
				normal(1),
				noAck(2)
				}
			MAX-ACCESS read-write
			STATUS current
			DESCRIPTION 
				"This object indicates the EDCA parameter AckPolicy for BE services on APs. The default value is 1."
			::= { hw5gRadioProfileEntry 37 }

		 --1.3.6.1.4.1.2011.6.139.11.1.17.1.38
		hw5gRadioApEDCABKECWmax OBJECT-TYPE
			SYNTAX Unsigned32 (0..15)
			MAX-ACCESS read-write
			STATUS current
			DESCRIPTION 
				"This object indicates the EDCA parameter ECWmax, namely, exponent form of Cwmax, for BK services on APs. ECWmin and ECWmax determine the average backoff time (ECWmax > ECWmin). The default value is 10."
			::= { hw5gRadioProfileEntry 38 }

		 --1.3.6.1.4.1.2011.6.139.11.1.17.1.39
		hw5gRadioApEDCABKECWmin OBJECT-TYPE
			SYNTAX Unsigned32 (0..15)
			MAX-ACCESS read-write
			STATUS current
			DESCRIPTION 
				"This object indicates the EDCA parameter ECWmin, namely, exponent form of Cwmin, for BK services on APs. ECWmin and ECWmax determine the average backoff time (ECWmax > ECWmin). The default value is 4."
			::= { hw5gRadioProfileEntry 39 }

		 --1.3.6.1.4.1.2011.6.139.11.1.17.1.40
		hw5gRadioApEDCABKAIFSN OBJECT-TYPE
			SYNTAX Unsigned32 (1..15)
			MAX-ACCESS read-write
			STATUS current
			DESCRIPTION 
				"This object indicates the EDCA parameter AIFSN, namely, arbitration interframe spacing number, for BK services on APs. The default value is 7.."
			::= { hw5gRadioProfileEntry 40 }

		 --1.3.6.1.4.1.2011.6.139.11.1.17.1.41
		hw5gRadioApEDCABKTXOPLimit OBJECT-TYPE
			SYNTAX Unsigned32 (0..255)
			MAX-ACCESS read-write
			STATUS current
			DESCRIPTION 
				"This object indicates the EDCA parameter TXOPLimit, namely, transmission opportunity limit, for BK services on APs. The default value is 0. The unit is 32 us."
			::= { hw5gRadioProfileEntry 41 }

		 --1.3.6.1.4.1.2011.6.139.11.1.17.1.42
		hw5gRadioApEDCABKAckPolicy OBJECT-TYPE
			SYNTAX INTEGER
				{
				normal(1),
				noAck(2)
				}
			MAX-ACCESS read-write
			STATUS current
			DESCRIPTION 
				"This object indicates the EDCA parameter AckPolicy for BK services on APs. The default value is 1."
			::= { hw5gRadioProfileEntry 42 }

		 --1.3.6.1.4.1.2011.6.139.11.1.17.1.43
		hw5gRadioWmmSwitch OBJECT-TYPE
			SYNTAX INTEGER
				{
				disable(1) ,
				enable(2)
				}
			MAX-ACCESS read-write
			STATUS current
			DESCRIPTION 
				"This object indicates the status of the WMM function. The default value is 2."
			::= { hw5gRadioProfileEntry 43 }

		 --1.3.6.1.4.1.2011.6.139.11.1.17.1.44
		hw5gRadioRtsCtsThreshold OBJECT-TYPE
			SYNTAX Unsigned32 (64..2347)
			MAX-ACCESS read-write
			STATUS current
			DESCRIPTION 
				"This object indicates the request To Send/Clear To Send (RTS/CTS) threshold. If the length of a frame to be sent by the MAC Layer exceeds this threshold, an RTS frame needs to be sent before this frame. The default value is 2347 bytes."
			::= { hw5gRadioProfileEntry 44 }

		 --1.3.6.1.4.1.2011.6.139.11.1.17.1.45
		hw5gRadioRtsCtsMode OBJECT-TYPE
			SYNTAX INTEGER
				{
				disable(1) ,
				ctsToSelf(2)  ,
				rtsCts(3)
				}
			MAX-ACCESS read-write
			STATUS current
			DESCRIPTION 
				"This object indicates the RTS-CTS mode set for the specified radio profile. The default value is 2."
			::= { hw5gRadioProfileEntry 45 }

		 --1.3.6.1.4.1.2011.6.139.11.1.17.1.46
		hw5gRadioPowerAutoAdjustSwitch OBJECT-TYPE
			SYNTAX INTEGER
				{
				disable(1) ,
				enable(2)
				}
			MAX-ACCESS read-write
			STATUS current
			DESCRIPTION 
				"This object indicates the status of the user-by-user power control function. The default value is 1."
			::= { hw5gRadioProfileEntry 46 }

		 --1.3.6.1.4.1.2011.6.139.11.1.17.1.47
		hw5gRadioBeamformingSwitch OBJECT-TYPE
			SYNTAX INTEGER
				{
				disable(1) ,
				enable(2)
				}
			MAX-ACCESS read-write
			STATUS current
			DESCRIPTION 
				"This object indicates the status of the beamforming function. The default value is 1."
			::= { hw5gRadioProfileEntry 47 }

		 --1.3.6.1.4.1.2011.6.139.11.1.17.1.48
		hw5gRadioWifiLight OBJECT-TYPE
			SYNTAX INTEGER
				{
				signalStrength(1) ,
				traffic(2)
				}
			MAX-ACCESS read-write
			STATUS current
			DESCRIPTION 
				"This object indicates information reflected by the blinking frequency of the Wireless LED on an AP. The default value is 1 NOTE ?	If Mesh is enabled on an AP, the Wireless indicator blinking frequency reflects the signal strength of the AP with the weakest signal among received signals from all neighboring APs.?	If WDS is enabled on an AP, the the Wireless indicator blinking frequency reflects the signal strength of the connected WDS AP.?	For a Leaf AP, the Wireless indicator blinking frequency reflects the signal strength of the connected Middle AP.?	For a Middle AP, the Wireless indicator blinking frequency reflects the signal strength of the connected Root AP.?	For a root AP, the Wireless indicator blinking frequency reflects the signal strength of the connected Middle AP with the weakest signal.?	If WDS or Mesh is not enabled on an AP, the Wireless indicator blinking frequency reflects the service traffic volume on the radio."
			::= { hw5gRadioProfileEntry 48 }

		 --1.3.6.1.4.1.2011.6.139.11.1.17.1.49
		hw5gRadioChannelSwitchAnnouncementSwitch OBJECT-TYPE
			SYNTAX INTEGER
				{
				disable(1) ,
				enable(2)
				}
			MAX-ACCESS read-write
			STATUS current
			DESCRIPTION 
				"This object indicates the status of the channel switchover announcement function. The default value is 1."
			::= { hw5gRadioProfileEntry 49 }

		 --1.3.6.1.4.1.2011.6.139.11.1.17.1.50
		hw5gRadioChannelSwitchMode OBJECT-TYPE
			SYNTAX INTEGER
				{
				continueTransmitting(1) ,
				stopTransmitting(2)
				}
			MAX-ACCESS read-write
			STATUS current
			DESCRIPTION 
				"This object indicates the channel switch announcement mode. The default value is 1."
			::= { hw5gRadioProfileEntry 50 }

		 --1.3.6.1.4.1.2011.6.139.11.1.17.1.51
		hw5gRadioAutoOffServiceSwitch OBJECT-TYPE
			SYNTAX INTEGER
				{
				disable(1) ,
				enable(2)
				}
			MAX-ACCESS read-write
			STATUS current
			DESCRIPTION 
				"This object indicates the status of the scheduled radio disabling function. The default value is 1."
			::= { hw5gRadioProfileEntry 51 }

		 --1.3.6.1.4.1.2011.6.139.11.1.17.1.52
		hw5gRadioAutoOffServiceStartTime OBJECT-TYPE
			SYNTAX OCTET STRING (SIZE (1..11))
			MAX-ACCESS read-write
			STATUS current
			DESCRIPTION 
				"This object indicates the start time for disabling the radio. The value is in the format of hh:mm:ss NOTE ?	hh specifies the hour. The value is an integer that ranges from 0 to 23.?	mm specifies the minute. The value is an integer that ranges from 0 to 59.?	ss specifies the second. The value is an integer that ranges from 0 to 59.."
			::= { hw5gRadioProfileEntry 52 }

		 --1.3.6.1.4.1.2011.6.139.11.1.17.1.53
		hw5gRadioAutoOffServiceEndTime OBJECT-TYPE
			SYNTAX OCTET STRING (SIZE (1..11))
			MAX-ACCESS read-write
			STATUS current
			DESCRIPTION 
				"This object indicates the end time for disabling of the radio. The value is in the format of hh:mm:ss. NOTE?	hh specifies the hour. The value is an integer that ranges from 0 to 23.?	mm specifies the minute. The value is an integer that ranges from 0 to 59.?	ss specifies the second. The value is an integer that ranges from 0 to 59."
			::= { hw5gRadioProfileEntry 53 }

		 --1.3.6.1.4.1.2011.6.139.11.1.17.1.54
		hw5gRadioInterferenceDetectSwitch OBJECT-TYPE
			SYNTAX INTEGER
				{
				disable(1) ,
				enable(2)
				}
			MAX-ACCESS read-write
			STATUS current
			DESCRIPTION 
				"This object indicates the status of the user-by-user power control function. The default value is 1."
			::= { hw5gRadioProfileEntry 54 }

		 --1.3.6.1.4.1.2011.6.139.11.1.17.1.55
		hw5gRadioInterferenceIntraFrequencyThreshold OBJECT-TYPE
			SYNTAX Unsigned32 (1..100)
			MAX-ACCESS read-write
			STATUS current
			DESCRIPTION 
				"This object indicates the alarm threshold for co-channel interference, namely, the percentage of the co-channel interference power against the maximum power. The default value is 50. "
			::= { hw5gRadioProfileEntry 55 }

		 --1.3.6.1.4.1.2011.6.139.11.1.17.1.56
		hw5gRadioInterferenceAdjacentFrequencyThreshold OBJECT-TYPE
			SYNTAX Unsigned32 (1..100)
			MAX-ACCESS read-write
			STATUS current
			DESCRIPTION 
				"This object indicates the alarm threshold for adjacent-channel interference, namely, the percentage of the adjacent-channel interference power against the maximum power. The default value is 50."
			::= { hw5gRadioProfileEntry 56 }

		 --1.3.6.1.4.1.2011.6.139.11.1.17.1.57
		hw5gRadioInterferenceStationThreshold OBJECT-TYPE
			SYNTAX Unsigned32 (1..256)
			MAX-ACCESS read-write
			STATUS current
			DESCRIPTION 
				"This object indicates the alarm threshold for adjacent-channel interference. When the number of the STAs detected exceeds the specified alarm threshold, the AP reports alarms to the AC. The default value is 32."
			::= { hw5gRadioProfileEntry 57 }

		 --1.3.6.1.4.1.2011.6.139.11.1.17.1.58
		hw5gRadioRrmProfile OBJECT-TYPE
			SYNTAX OCTET STRING (SIZE (1..35))
			MAX-ACCESS read-write
			STATUS current
			DESCRIPTION 
				"This object indicates the bound RRM profile."
			::= { hw5gRadioProfileEntry 58 }

		 --1.3.6.1.4.1.2011.6.139.11.1.17.1.59
		hw5gRadioAirScanProfile OBJECT-TYPE
			SYNTAX OCTET STRING (SIZE (1..35))
			MAX-ACCESS read-write
			STATUS current
			DESCRIPTION 
				"This object indicates the bound air scan profile."
			::= { hw5gRadioProfileEntry 59 }

		 --1.3.6.1.4.1.2011.6.139.11.1.17.1.60
		hw5gRadioProfileRowStatus OBJECT-TYPE
			SYNTAX RowStatus
			MAX-ACCESS read-write
			STATUS current
			DESCRIPTION 
				"This object indicates the row status of this table. ROWSTATUS_CREATEANDFLOW and ROWSTATUS_DESTROY are commonly used.?	ROWSTATUS_UNDEFINED: undefined?	ROWSTATUS_ACTIVE: active?	ROWSTATUS_NOTINSERVICE: notInService?	ROWSTATUS_NOTREADY: notReady?	ROWSTATUS_CREATEANDFLOW: createAndGo?	ROWSTATUS_CREATEANDWAIT: createAndWait?	ROWSTATUS_DESTROY: destroy."
			::= { hw5gRadioProfileEntry 60 }

		-- 1.3.6.1.4.1.2011.6.139.11.1.17.1.61
		hw5gRadioProfileUtmostPowerSwitch OBJECT-TYPE
			SYNTAX INTEGER
				{
				disable(1),
				enable(2)
				}
			MAX-ACCESS read-write
			STATUS current
			DESCRIPTION
				"This object indicates the switch for the function of sending packets at maximum power."
			::= { hw5gRadioProfileEntry 61 }
				
		-- 1.3.6.1.4.1.2011.6.139.11.1.17.1.63
		hw5gRadioProfileRadioType OBJECT-TYPE
			SYNTAX INTEGER
				{
				dot11a(2),
				dot11n(6),
				dot11ac(14)
				}
			MAX-ACCESS read-write
			STATUS current
			DESCRIPTION
				"This object indicates the type of radio. The default value is 14. "
			::= { hw5gRadioProfileEntry 63 }

		-- 1.3.6.1.4.1.2011.6.139.11.1.17.1.64
		hw5gRadioProfileSmartAntennaEnable OBJECT-TYPE
			SYNTAX INTEGER
				{
				disable(1),
				enable(2)
				}
			MAX-ACCESS read-write
			STATUS current
			DESCRIPTION
				"Description."
			DEFVAL { disable }
			::= { hw5gRadioProfileEntry 64 }

		-- 1.3.6.1.4.1.2011.6.139.11.1.17.1.65
		hw5gRadioProfileMuMIMOEnable OBJECT-TYPE
			SYNTAX INTEGER
				{
				disable(1),
				enable(2)
				}
			MAX-ACCESS read-write
			STATUS current
			DESCRIPTION
				"Description."
			DEFVAL { disable }
			::= { hw5gRadioProfileEntry 65 }
			
		-- 1.3.6.1.4.1.2011.6.139.11.1.17.1.66
		hw5gRadioProfileTxChainNum OBJECT-TYPE
			SYNTAX Unsigned32 (1..4)
			MAX-ACCESS read-write
			STATUS current
			DESCRIPTION
				"Description."
			DEFVAL { 4 }
			::= { hw5gRadioProfileEntry 66 }
			
		-- 1.3.6.1.4.1.2011.6.139.11.1.17.1.67
		hw5gRadioProfileRxChainNum OBJECT-TYPE
			SYNTAX Unsigned32 (1..4)
			MAX-ACCESS read-write
			STATUS current
			DESCRIPTION
				"Description."
			DEFVAL { 4 }
			::= { hw5gRadioProfileEntry 67 }
			
		-- 1.3.6.1.4.1.2011.6.139.11.1.18
		hwRrmProfileTable OBJECT-TYPE
			SYNTAX SEQUENCE OF HwRrmProfileEntry 
			MAX-ACCESS not-accessible
			STATUS current
			DESCRIPTION 
				"This table is used to configure radio resource management parameters, including parameters related to band steering, dynamic load balancing, smart roaming, and UAC."
			::= { hwWlanConfigObjects 18 }

		--1.3.6.1.4.1.2011.6.139.11.1.18.1
		hwRrmProfileEntry OBJECT-TYPE
			SYNTAX HwRrmProfileEntry 
			MAX-ACCESS not-accessible
			STATUS current
			DESCRIPTION 
				"The index of this table is hwRrmProfileName."
			INDEX { hwRrmProfileName }
			::= { hwRrmProfileTable 1 }


		HwRrmProfileEntry ::=
			SEQUENCE {				
				hwRrmProfileName
					OCTET STRING,
				hwRrmAutoChannelSelectSwitch
					INTEGER,
				hwRrmAutoTxPowerSelectSwitch
					INTEGER,
				hwRrmErrRateThreshold
					Unsigned32,
				hwRrmAirtimeFairSchduleSwitch
					INTEGER,
				hwRrmDynamicEdcaSwitch
					INTEGER,
				hwRrmUacLimitClientSnrSwitch
					INTEGER,
				hwRrmUacClientSnrThreshold
					Unsigned32,
				hwRrmUacPolicySwitch
					INTEGER,
				hwRrmUacPolicyType
					INTEGER,
				hwRrmUacClientNumAccessThreshold
					Unsigned32,
				hwRrmUacClientNumRoamThreshold
					Unsigned32,
				hwRrmUacReachThresholdHideSsidSwitch
					INTEGER,
				hwRrmBandSteerDenyThreshold
					Unsigned32,
				hwRrmBandSteerLbClientThreshold
					Unsigned32,
				hwRrmBandSteerLbGapThreshold
					Unsigned32,
				hwRrmBandSteerClientBandsExpire
					Unsigned32,
				hwRrmLoadBalanceSwitch
					INTEGER,
				hwRrmLoadBalanceClientThreshold
					Unsigned32,
				hwRrmLoadBalanceGapThreshold
					Unsigned32,
				hwRrmLoadBalanceDenyThreshold
					Unsigned32,
				hwRrmSmartRoamCheckType
					INTEGER,
				hwRrmSmartRoamSwitch
					INTEGER,
				hwRrmSmartRoamSnrThreshold
					Unsigned32,
				hwRrmSmartRoamRateThreshold
					Unsigned32,
				hwRrmSmartRoamSnrHighLevelMargin
					Unsigned32,
				hwRrmSmartRoamSnrLowLevelMargin
					Unsigned32,
				hwRrmSmartRoamSnrCheckInterval
					Unsigned32,
				hwRrmSmartRoamUnableRoamExpireTime
					Unsigned32,
				hwRrmProfileRowStatus
					RowStatus,
				hwRrmUacChannelUtiAccessThreshold
					Unsigned32,
				hwRrmUacChannelUtiRoamThreshold
					Unsigned32
			 }

		 --1.3.6.1.4.1.2011.6.139.11.1.18.1.1
		hwRrmProfileName OBJECT-TYPE
			SYNTAX OCTET STRING (SIZE (1..35))
			MAX-ACCESS not-accessible
			STATUS current
			DESCRIPTION 
				"This object indicates the name of the RRM profile. It is the index of the table."
			::= { hwRrmProfileEntry 1 }

		 --1.3.6.1.4.1.2011.6.139.11.1.18.1.2
		hwRrmAutoChannelSelectSwitch OBJECT-TYPE
			SYNTAX INTEGER
				{
				disable(1) ,
				enable(2)
				}
			MAX-ACCESS read-write
			STATUS current
			DESCRIPTION 
				"This object indicates the status of the automatic channel selection function. The default value is 2."
			::= { hwRrmProfileEntry 2 }

		 --1.3.6.1.4.1.2011.6.139.11.1.18.1.3
		hwRrmAutoTxPowerSelectSwitch OBJECT-TYPE
			SYNTAX INTEGER
				{
				disable(1) ,
				enable(2)
				}
			MAX-ACCESS read-write
			STATUS current
			DESCRIPTION 
				"This object indicates the status of the automatic power selection function. The default value is 2."
			::= { hwRrmProfileEntry 3 }

		 --1.3.6.1.4.1.2011.6.139.11.1.18.1.4
		hwRrmErrRateThreshold OBJECT-TYPE
			SYNTAX Unsigned32 (20..80)
			MAX-ACCESS read-write
			STATUS current
			DESCRIPTION 
				"This object indicate the error packet threshold triggering the automatic channel or power selection function. The default value is 50. It is expressed in percentage."
			::= { hwRrmProfileEntry 4 }

		 --1.3.6.1.4.1.2011.6.139.11.1.18.1.5
		hwRrmAirtimeFairSchduleSwitch OBJECT-TYPE
			SYNTAX INTEGER
				{
				disable(1) ,
				enable(2)
				}
			MAX-ACCESS read-write
			STATUS current
			DESCRIPTION 
				"This object indicates the status of the airtime scheduling function. The default value is 1."
			::= { hwRrmProfileEntry 5 }

		 --1.3.6.1.4.1.2011.6.139.11.1.18.1.6
		hwRrmDynamicEdcaSwitch OBJECT-TYPE
			SYNTAX INTEGER
				{
				disable(1) ,
				enable(2)
				}
			MAX-ACCESS read-write
			STATUS current
			DESCRIPTION 
				"This object indicates the status of the dynamic EDCA parameter adjustment function. The default value is 1."
			::= { hwRrmProfileEntry 6 }

		 --1.3.6.1.4.1.2011.6.139.11.1.18.1.7
		hwRrmUacLimitClientSnrSwitch OBJECT-TYPE
			SYNTAX INTEGER
				{
				disable(1) ,
				enable(2)
				}
			MAX-ACCESS read-write
			STATUS current
			DESCRIPTION 
				"This object indicates the status of the rejecting access from terminals with weak signals function. The default value is 1."
			::= { hwRrmProfileEntry 7 }

		 --1.3.6.1.4.1.2011.6.139.11.1.18.1.8
		hwRrmUacClientSnrThreshold OBJECT-TYPE
			SYNTAX Unsigned32 (5..75|255)
			MAX-ACCESS read-write
			STATUS current
			DESCRIPTION 
				"This object indicates the SNR threshold for rejecting access from terminals. The default value is 15. It is expressed in dB."
			::= { hwRrmProfileEntry 8 }

		 --1.3.6.1.4.1.2011.6.139.11.1.18.1.9
		hwRrmUacPolicySwitch OBJECT-TYPE
			SYNTAX INTEGER
				{
				disable(1) ,
				enable(2)
				}
			MAX-ACCESS read-write
			STATUS current
			DESCRIPTION 
				"This object indicates the status of the UAC policy function. The default value is 1."
			::= { hwRrmProfileEntry 9 }

		 --1.3.6.1.4.1.2011.6.139.11.1.18.1.10
		hwRrmUacPolicyType OBJECT-TYPE
			SYNTAX INTEGER
				{
				users(1) ,
				channelUtilization(2),
				unknown(255)
				}
			MAX-ACCESS read-write
			STATUS current
			DESCRIPTION 
				"This object indicates the UAC policy. The default value is 1."
			::= { hwRrmProfileEntry 10 }

		 --1.3.6.1.4.1.2011.6.139.11.1.18.1.11
		hwRrmUacClientNumAccessThreshold OBJECT-TYPE
			SYNTAX Unsigned32 (1..128)
			MAX-ACCESS read-write
			STATUS current
			DESCRIPTION 
				"Description."
			::= { hwRrmProfileEntry 11 }

		 --1.3.6.1.4.1.2011.6.139.11.1.18.1.12
		hwRrmUacClientNumRoamThreshold OBJECT-TYPE
			SYNTAX Unsigned32 (1..128)
			MAX-ACCESS read-write
			STATUS current
			DESCRIPTION 
				"Description."
			::= { hwRrmProfileEntry 12 }

		 --1.3.6.1.4.1.2011.6.139.11.1.18.1.13
		hwRrmUacReachThresholdHideSsidSwitch OBJECT-TYPE
			SYNTAX INTEGER
				{
				disable(1) ,
				enable(2)
				}
			MAX-ACCESS read-write
			STATUS current
			DESCRIPTION 
				"This object indicates the status of the function of hiding the SSID when the value of UAC reaches the specified threshold. The default value is 1."
			::= { hwRrmProfileEntry 13 }

		 --1.3.6.1.4.1.2011.6.139.11.1.18.1.14
		hwRrmBandSteerDenyThreshold OBJECT-TYPE
			SYNTAX Unsigned32 (1..10)
			MAX-ACCESS read-write
			STATUS current
			DESCRIPTION 
				"This object indicates the maximum number of times the band steering function rejects association requests from terminals. The default value is 2."
			::= { hwRrmProfileEntry 14 }

		 --1.3.6.1.4.1.2011.6.139.11.1.18.1.15
		hwRrmBandSteerLbClientThreshold OBJECT-TYPE
			SYNTAX Unsigned32 (0..100)
			MAX-ACCESS read-write
			STATUS current
			DESCRIPTION 
				"This object indicates the minimum number of terminals for triggering inter-band load balancing. The default value is 10.."
			::= { hwRrmProfileEntry 15 }

		 --1.3.6.1.4.1.2011.6.139.11.1.18.1.16
		hwRrmBandSteerLbGapThreshold OBJECT-TYPE
			SYNTAX Unsigned32 (1..100)
			MAX-ACCESS read-write
			STATUS current
			DESCRIPTION 
				"Description."
			::= { hwRrmProfileEntry 16 }

		 --1.3.6.1.4.1.2011.6.139.11.1.18.1.17
		hwRrmBandSteerClientBandsExpire OBJECT-TYPE
			SYNTAX Unsigned32 (10..300)
			MAX-ACCESS read-write
			STATUS current
			DESCRIPTION 
				"This object indicates the load difference percentage for triggering inter-band load balancing. The default value is 20."
			::= { hwRrmProfileEntry 17 }

		 --1.3.6.1.4.1.2011.6.139.11.1.18.1.18
		hwRrmLoadBalanceSwitch OBJECT-TYPE
			SYNTAX INTEGER
				{
				disable(1) ,
				enable(2)
				}
			MAX-ACCESS read-write
			STATUS current
			DESCRIPTION 
				"This object indicates the status of the load balancing group function. The default value is 1."
			::= { hwRrmProfileEntry 18 }

		 --1.3.6.1.4.1.2011.6.139.11.1.18.1.19
		hwRrmLoadBalanceClientThreshold OBJECT-TYPE
			SYNTAX Unsigned32 (1..100)
			MAX-ACCESS read-write
			STATUS current
			DESCRIPTION 
				"This object indicates the percentage of terminals for triggering load balancing. The default value is 10. It is expressed in percentage."
			::= { hwRrmProfileEntry 19 }

		 --1.3.6.1.4.1.2011.6.139.11.1.18.1.20
		hwRrmLoadBalanceGapThreshold OBJECT-TYPE
			SYNTAX Unsigned32 (1..100)
			MAX-ACCESS read-write
			STATUS current
			DESCRIPTION 
				"This object indicates the load difference threshold for triggering load balancing, which is expressed in the number of terminals. The default value is 10."
			::= { hwRrmProfileEntry 20 }

		 --1.3.6.1.4.1.2011.6.139.11.1.18.1.21
		hwRrmLoadBalanceDenyThreshold OBJECT-TYPE
			SYNTAX Unsigned32 (1..10)
			MAX-ACCESS read-write
			STATUS current
			DESCRIPTION 
				"This object indicates the maximum number of times the load balancing function rejects association requests from terminals. The default value is 3."
			::= { hwRrmProfileEntry 21 }

		 --1.3.6.1.4.1.2011.6.139.11.1.18.1.22
		hwRrmSmartRoamCheckType OBJECT-TYPE
			SYNTAX INTEGER
				{
				checkSnr(1) ,
				checkRate(2),
				checkAll(3)
				}			
			MAX-ACCESS read-write
			STATUS current
			DESCRIPTION 
				"This object indicates whether STA active roaming is triggered by rate check or SNR check.The values are as follows:?	1: checkSnr?	2: checkRate?	3: checkAll."
			::= { hwRrmProfileEntry 22 }

		 --1.3.6.1.4.1.2011.6.139.11.1.18.1.23
		hwRrmSmartRoamSwitch OBJECT-TYPE
			SYNTAX INTEGER
				{
				disable(1) ,
				enable(2)
				}
			MAX-ACCESS read-write
			STATUS current
			DESCRIPTION 
				"This object indicates the status of the smart roaming function. The default value is 1."
			::= { hwRrmProfileEntry 23 }

		 --1.3.6.1.4.1.2011.6.139.11.1.18.1.24
		hwRrmSmartRoamSnrThreshold OBJECT-TYPE
			SYNTAX Unsigned32 (5..75)
			MAX-ACCESS read-write
			STATUS current
			DESCRIPTION 
				"This object indicates the SNR threshold for triggering the smart roaming function. The default value is 20 dB."
			::= { hwRrmProfileEntry 24 }

		 --1.3.6.1.4.1.2011.6.139.11.1.18.1.25
		hwRrmSmartRoamRateThreshold OBJECT-TYPE
			SYNTAX Unsigned32 (1..100)
			MAX-ACCESS read-write
			STATUS current
			DESCRIPTION 
				"This object indicates the rate threshold for triggering the smart roaming function. It is expressed in the percentage against the maximum rate supported by the terminal. The default value is 0. It is expressed in percentage."
			::= { hwRrmProfileEntry 25 }

		 --1.3.6.1.4.1.2011.6.139.11.1.18.1.26
		hwRrmSmartRoamSnrHighLevelMargin OBJECT-TYPE
			SYNTAX Unsigned32 (10..20)
			MAX-ACCESS read-write
			STATUS current
			DESCRIPTION 
				"This object indicates the upper SNR difference threshold for triggering smart roaming. The default value is 15. It is expressed in dB."
			::= { hwRrmProfileEntry 26 }

		 --1.3.6.1.4.1.2011.6.139.11.1.18.1.27
		hwRrmSmartRoamSnrLowLevelMargin OBJECT-TYPE
			SYNTAX Unsigned32 (3..15)
			MAX-ACCESS read-write
			STATUS current
			DESCRIPTION 
				"This object indicates the lower SNR difference threshold for triggering smart roaming. The default value is 6. It is expressed in dB."
			::= { hwRrmProfileEntry 27 }

		 --1.3.6.1.4.1.2011.6.139.11.1.18.1.28
		hwRrmSmartRoamSnrCheckInterval OBJECT-TYPE
			SYNTAX Unsigned32 (3..30)
			MAX-ACCESS read-write
			STATUS current
			DESCRIPTION 
				"This object indicates the terminal SNR detection interval for smart roaming. The default value is 3. It is expressed in s."
			::= { hwRrmProfileEntry 28 }

		 --1.3.6.1.4.1.2011.6.139.11.1.18.1.29
		hwRrmSmartRoamUnableRoamExpireTime OBJECT-TYPE
			SYNTAX Unsigned32 (30..2880)
			MAX-ACCESS read-write
			STATUS current
			DESCRIPTION 
				"This object indicates the aging time of records that terminals are unable to roam. The default value is 240. It is expressed in minutes."
			::= { hwRrmProfileEntry 29 }

		 --1.3.6.1.4.1.2011.6.139.11.1.18.1.30
		hwRrmProfileRowStatus OBJECT-TYPE
			SYNTAX RowStatus
			MAX-ACCESS read-write
			STATUS current
			DESCRIPTION 
				"This object indicates the row status of this table. ROWSTATUS_CREATEANDFLOW and ROWSTATUS_DESTROY are commonly used."
			::= { hwRrmProfileEntry 30 }

		
		-- 1.3.6.1.4.1.2011.6.139.11.1.18.1.31
		hwRrmUacChannelUtiAccessThreshold OBJECT-TYPE
			SYNTAX Unsigned32 (1..100)
			MAX-ACCESS read-write
			STATUS current
			DESCRIPTION
				"Description."
			::= { hwRrmProfileEntry 31 }

		
		-- 1.3.6.1.4.1.2011.6.139.11.1.18.1.32
		hwRrmUacChannelUtiRoamThreshold OBJECT-TYPE
			SYNTAX Unsigned32 (1..100)
			MAX-ACCESS read-write
			STATUS current
			DESCRIPTION
				"Description."
			::= { hwRrmProfileEntry 32 }

		
		--1.3.6.1.4.1.2011.6.139.11.1.19
		hwAirScanProfileTable OBJECT-TYPE
			SYNTAX SEQUENCE OF HwAirScanProfileEntry 
			MAX-ACCESS not-accessible
			STATUS current
			DESCRIPTION 
				"This table is used to configure air scan intervals, duration, and scan channel sets."
			::= { hwWlanConfigObjects 19 }

		--1.3.6.1.4.1.2011.6.139.11.1.19.1
		hwAirScanProfileEntry OBJECT-TYPE
			SYNTAX HwAirScanProfileEntry 
			MAX-ACCESS not-accessible
			STATUS current
			DESCRIPTION 
				"The index of this table is hwAirScanProfileName."
			INDEX { hwAirScanProfileName }
			::= { hwAirScanProfileTable 1 }


		HwAirScanProfileEntry ::=
			SEQUENCE {				
				hwAirScanProfileName
					OCTET STRING,
				hwAirScanPeriod
					Unsigned32,
				hwAirScanInterval
					Unsigned32,
				hwAirScanChannelSet
					INTEGER,
				hwAirScanProfilRowStatus
					RowStatus,
				hwAirScanVoiceAware
					INTEGER,
				hwAirScanVideoAware
					INTEGER
			 }

		 --1.3.6.1.4.1.2011.6.139.11.1.19.1.1
		hwAirScanProfileName OBJECT-TYPE
			SYNTAX OCTET STRING (SIZE (1..35))
			MAX-ACCESS not-accessible
			STATUS current
			DESCRIPTION 
				"This object indicates the name of an air scan profile. It is the index of the table."
			::= { hwAirScanProfileEntry 1 }

		 --1.3.6.1.4.1.2011.6.139.11.1.19.1.2
		hwAirScanPeriod OBJECT-TYPE
			SYNTAX Unsigned32 (60..100)
			MAX-ACCESS read-write
			STATUS current
			DESCRIPTION 
				"This object indicates the air scan period. The default value is 60. It is expressed in ms."
			::= { hwAirScanProfileEntry 2 }

		 --1.3.6.1.4.1.2011.6.139.11.1.19.1.3
		hwAirScanInterval OBJECT-TYPE
			SYNTAX Unsigned32 (300..600000)
			MAX-ACCESS read-write
			STATUS current
			DESCRIPTION 
				"This object indicates the scan interval. The default value is 600. The unit is 0.1s."
			::= { hwAirScanProfileEntry 3 }

		 --1.3.6.1.4.1.2011.6.139.11.1.19.1.4
		hwAirScanChannelSet OBJECT-TYPE
			SYNTAX INTEGER
				{
				countryChannel(1),
				dcaChannel(2),
				workChannel(3)
				}
			MAX-ACCESS read-write
			STATUS current
			DESCRIPTION 
				"This object indicates the scan channel set. The default value is 1."
			::= { hwAirScanProfileEntry 4 }

			--1.3.6.1.4.1.2011.6.139.11.1.19.1.5
		hwAirScanProfilRowStatus OBJECT-TYPE
			SYNTAX RowStatus
			MAX-ACCESS read-write
			STATUS current
			DESCRIPTION 
				"This object indicates the row status of this table. ROWSTATUS_CREATEANDFLOW and ROWSTATUS_DESTROY are commonly used.?	ROWSTATUS_UNDEFINED: undefined?	ROWSTATUS_ACTIVE: active?	ROWSTATUS_NOTINSERVICE: notInService?	ROWSTATUS_NOTREADY: notReady?	ROWSTATUS_CREATEANDFLOW: createAndGo?	ROWSTATUS_CREATEANDWAIT: createAndWait?	ROWSTATUS_DESTROY: destroy."
			::= { hwAirScanProfileEntry 5 }
			
		 --1.3.6.1.4.1.2011.6.139.11.1.19.1.6
		hwAirScanVoiceAware OBJECT-TYPE
			SYNTAX INTEGER
				{
				disable(1),
				enable(2)
				}
			MAX-ACCESS read-write
			STATUS current
			DESCRIPTION 
				"This object indicates the voice aware set. The default value is enable."
			::= { hwAirScanProfileEntry 6 }

		 --1.3.6.1.4.1.2011.6.139.11.1.19.1.7
		hwAirScanVideoAware OBJECT-TYPE
			SYNTAX INTEGER
				{
				disable(1),
				enable(2)
				}
			MAX-ACCESS read-write
			STATUS current
			DESCRIPTION 
				"This object indicates the video aware set. The default value is enable."
			::= { hwAirScanProfileEntry 7 }
						
		--1.3.6.1.4.1.2011.6.139.11.1.20
		hwVapProfileTable OBJECT-TYPE
			SYNTAX SEQUENCE OF HwVapProfileEntry 
			MAX-ACCESS not-accessible
			STATUS current
			DESCRIPTION 
				"This table is used to configure and query VAP profile parameters."
			::= { hwWlanConfigObjects 20 }

		--1.3.6.1.4.1.2011.6.139.11.1.20.1
		hwVapProfileEntry OBJECT-TYPE
			SYNTAX HwVapProfileEntry 
			MAX-ACCESS not-accessible
			STATUS current
			DESCRIPTION 
				"The index of this table is hwVapProfileName."
			INDEX { hwVapProfileName }
			::= { hwVapProfileTable 1 }


		HwVapProfileEntry ::=
			SEQUENCE {				
				hwVapProfileName
					OCTET STRING,
				hwVapForwardMode
					INTEGER,
				hwVapTunnelForwardProtocol
					Unsigned32,
				hwVapServiceSwitch
					INTEGER,
				hwVapAutoOffStartTime
					OCTET STRING,
				hwVapAutoOffEndTime
					OCTET STRING,
				hwVapTemporaryManagementSwitch
					INTEGER,
				hwVapServiceVlan
					Unsigned32,
				hwVapVlanPool
					OCTET STRING,
				hwVapType
					INTEGER,
				hwVapStaAccessMode
					INTEGER,
				hwVapStaAccessModePorfile
					OCTET STRING,
				hwVapRoamHomeAgent
					INTEGER,
				hwVapRoamVlanMobilityGroup
					Unsigned32,
				hwVapRoamLayer3Switch
					INTEGER,
				hwVapBandSteerSwitch
					INTEGER,
				hwVapLearnIpv4Address
					INTEGER,
				hwVapLearnIpv6Address
					INTEGER,
				hwVapLearnIpv4AddressStrict
					INTEGER,
				hwVapIpBindCheck
					INTEGER,
				hwVapArpBindCheck
					INTEGER,
				hwVapOptinon82InsertSwitch
					INTEGER,
				hwVapOptinon82InsertRidFormat
					INTEGER,
				hwVapDhcpTrustPort
					INTEGER,
				hwVapNdTrustPort
					INTEGER,
				hwVapSecurityProfile
					OCTET STRING,
				hwVapTrafficProfile
					OCTET STRING,
				hwVapSsidProfile
					OCTET STRING,
				hwVapAuthenticationProfile
					OCTET STRING,
				hwVapSacProfile
					OCTET STRING,
				hwVapProfileRowStatus
					RowStatus,
				hwVapUserProfile
					OCTET STRING,
				hwVapHotspot2Profile
					OCTET STRING,
				hwSoftgreProfile
					OCTET STRING,
				hwVapOptinon82RidUserDefined
					OCTET STRING,
				hwVapOptinon82RidMacFormat
					INTEGER,
				hwVapOptinon82InsertCidFormat
					INTEGER,
				hwVapOptinon82CidUserDefined
					OCTET STRING,
				hwVapOptinon82CidMacFormat
					INTEGER,
				hwVapUccProfile
					OCTET STRING,
				hwVapAntiAttackBroadcastFloodSwitch
					INTEGER,
				hwVapAntiAttackBroadcastFloodStaRateThreshold
					Unsigned32,
				hwVapAntiAttackBroadcastFloodBlacklistSwitch
					INTEGER
			 }

		 --1.3.6.1.4.1.2011.6.139.11.1.20.1.1
		hwVapProfileName OBJECT-TYPE
			SYNTAX OCTET STRING (SIZE (1..35))
			MAX-ACCESS not-accessible
			STATUS current
			DESCRIPTION 
				"This object indicates the name of a VAP profile. It is the index of the table."
			::= { hwVapProfileEntry 1 }

		 --1.3.6.1.4.1.2011.6.139.11.1.20.1.2
		hwVapForwardMode OBJECT-TYPE
			SYNTAX INTEGER
				{
				unknown(1),
				directForward(2),
				tunnel(3),
				softgre(4)
				}
			MAX-ACCESS read-write
			STATUS current
			DESCRIPTION 
				"This object indicates the service forwarding mode. The default value is 1."
			::= { hwVapProfileEntry 2 }

		 --1.3.6.1.4.1.2011.6.139.11.1.20.1.3
		hwVapTunnelForwardProtocol OBJECT-TYPE
			SYNTAX Unsigned32
			MAX-ACCESS read-write
			STATUS current
			DESCRIPTION 
				"This object indicates the format of packets forwarded by tunnel. The default value is 0xF.?	bit0: dot1x?	bit1: http?	bit2: wapi?	bit3: mdns."
			::= { hwVapProfileEntry 3 }

		 --1.3.6.1.4.1.2011.6.139.11.1.20.1.4
		hwVapServiceSwitch OBJECT-TYPE
			SYNTAX INTEGER
				{
				disable(1) ,
				enable(2)
				}
			MAX-ACCESS read-write
			STATUS current
			DESCRIPTION 
				"This object indicates the status of the VAP service function. The default value is 2."
			::= { hwVapProfileEntry 4 }

		 --1.3.6.1.4.1.2011.6.139.11.1.20.1.5
		hwVapAutoOffStartTime OBJECT-TYPE
			SYNTAX OCTET STRING (SIZE (1..11))
			MAX-ACCESS read-write
			STATUS current
			DESCRIPTION 
				"This object indicates the start time of VAP profile. The format is HH:MM:SS."
			::= { hwVapProfileEntry 5 }

		 --1.3.6.1.4.1.2011.6.139.11.1.20.1.6
		hwVapAutoOffEndTime OBJECT-TYPE
			SYNTAX OCTET STRING (SIZE (1..11))
			MAX-ACCESS read-write
			STATUS current
			DESCRIPTION 
				"This object indicates the end time of VAP profile. The format is HH:MM:SS."
			::= { hwVapProfileEntry 6 }

		 --1.3.6.1.4.1.2011.6.139.11.1.20.1.7
		hwVapTemporaryManagementSwitch OBJECT-TYPE
			SYNTAX INTEGER
				{
				disable(1) ,
				enable(2)
				}
			MAX-ACCESS read-write
			STATUS current
			DESCRIPTION 
				"If this parameter is set to 2, the VAP automatically becomes the management VAP for offline APs after the AP is disconnected. It can still send signals so that maintenance personnel can access it to identify faults (the security mode is the non-authentication security mode and the SSID will be hidden). The default value is 1."
			::= { hwVapProfileEntry 7 }

		 --1.3.6.1.4.1.2011.6.139.11.1.20.1.8
		hwVapServiceVlan OBJECT-TYPE
			SYNTAX Unsigned32 (1..4094)
			MAX-ACCESS read-write
			STATUS current
			DESCRIPTION 
				"This object indicates the service VLAN for the VAP. The default value is 1."
			::= { hwVapProfileEntry 8 }

		 --1.3.6.1.4.1.2011.6.139.11.1.20.1.9
		hwVapVlanPool OBJECT-TYPE
			SYNTAX OCTET STRING (SIZE (0..31))
			MAX-ACCESS read-write
			STATUS current
			DESCRIPTION 
				"This object indicates the VLAN pool to which the VAP is bound."
			::= { hwVapProfileEntry 9 }

		 --1.3.6.1.4.1.2011.6.139.11.1.20.1.10
		hwVapType OBJECT-TYPE
			SYNTAX INTEGER
				{
				service(1) ,
				managementAp(2),
				managementAc(3)
				}
			MAX-ACCESS read-write
			STATUS current
			DESCRIPTION 
				"This object indicates the VAP type. The default value is 1."
			::= { hwVapProfileEntry 10 }

		 --1.3.6.1.4.1.2011.6.139.11.1.20.1.11
		hwVapStaAccessMode OBJECT-TYPE
			SYNTAX INTEGER
				{
				disable(1),
				blacklist(2),
				whitelist(3)
				}
			MAX-ACCESS read-write
			STATUS current
			DESCRIPTION 
				"This object indicates the access mode. The default value is 1."
			::= { hwVapProfileEntry 11 }

		 --1.3.6.1.4.1.2011.6.139.11.1.20.1.12
		hwVapStaAccessModePorfile OBJECT-TYPE
			SYNTAX OCTET STRING (SIZE (0..35))
			MAX-ACCESS read-write
			STATUS current
			DESCRIPTION 
				"This object indicates blacklist and whitelist profiles."
			::= { hwVapProfileEntry 12 }

		 --1.3.6.1.4.1.2011.6.139.11.1.20.1.13
		hwVapRoamHomeAgent OBJECT-TYPE
			SYNTAX INTEGER
				{
				ap(1),
				ac(2)
				}
			MAX-ACCESS read-write
			STATUS current
			DESCRIPTION 
				"This object indicates the tunnel endpoint for inter-Layer 3 roaming. The default value is 1.."
			::= { hwVapProfileEntry 13 }

		 --1.3.6.1.4.1.2011.6.139.11.1.20.1.14
		hwVapRoamVlanMobilityGroup OBJECT-TYPE
			SYNTAX Unsigned32 (1..4094)
			MAX-ACCESS read-write
			STATUS current
			DESCRIPTION 
				"This object indicates the VLAN group for roaming. For the same VLAN, if the VAP is in different VLAN groups for roaming, the roaming is also inter-Layer 3 roaming. The default value is 1.."
			::= { hwVapProfileEntry 14 }

		 --1.3.6.1.4.1.2011.6.139.11.1.20.1.15
		hwVapRoamLayer3Switch OBJECT-TYPE
			SYNTAX INTEGER
				{
				disable(1) ,
				enable(2)
				}
			MAX-ACCESS read-write
			STATUS current
			DESCRIPTION 
				"This object indicates the status of the Layer 3 roaming function. The default value is 2."
			::= { hwVapProfileEntry 15 }

		 --1.3.6.1.4.1.2011.6.139.11.1.20.1.16
		hwVapBandSteerSwitch OBJECT-TYPE
			SYNTAX INTEGER
				{
				disable(1) ,
				enable(2)
				}
			MAX-ACCESS read-write
			STATUS current
			DESCRIPTION 
				"This object indicates the status of the band steering function. The default value is 2."
			::= { hwVapProfileEntry 16 }

		 --1.3.6.1.4.1.2011.6.139.11.1.20.1.17
		hwVapLearnIpv4Address OBJECT-TYPE
			SYNTAX INTEGER
				{
				disable(1) ,
				enable(2)
				}
			MAX-ACCESS read-write
			STATUS current
			DESCRIPTION 
				"This object indicates the status of the IPv4 address learning function. The default value is 2."
			::= { hwVapProfileEntry 17 }

		 --1.3.6.1.4.1.2011.6.139.11.1.20.1.18
		hwVapLearnIpv6Address OBJECT-TYPE
			SYNTAX INTEGER
				{
				disable(1) ,
				enable(2)
				}
			MAX-ACCESS read-write
			STATUS current
			DESCRIPTION 
				"This object indicates the status of the IPv6 address learning function. The default value is 2."
			::= { hwVapProfileEntry 18 }

		 --1.3.6.1.4.1.2011.6.139.11.1.20.1.19
		hwVapLearnIpv4AddressStrict OBJECT-TYPE
			SYNTAX INTEGER
				{
				disable(1) ,
				enable(2) ,
				enableBlacklist(3)
				}
			MAX-ACCESS read-write
			STATUS current
			DESCRIPTION 
				"This object indicates the status of the strict address learning (only through the DHCP) function. The default value is 1."
			::= { hwVapProfileEntry 19 }

		 --1.3.6.1.4.1.2011.6.139.11.1.20.1.20
		hwVapIpBindCheck OBJECT-TYPE
			SYNTAX INTEGER
				{
				disable(1) ,
				enable(2)
				}
			MAX-ACCESS read-write
			STATUS current
			DESCRIPTION 
				"This object indicates the status of the IP binding relationship check function. The default value is 1."
			::= { hwVapProfileEntry 20 }

		 --1.3.6.1.4.1.2011.6.139.11.1.20.1.21
		hwVapArpBindCheck OBJECT-TYPE
			SYNTAX INTEGER
				{
				disable(1) ,
				enable(2)
				}
			MAX-ACCESS read-write
			STATUS current
			DESCRIPTION 
				"This object indicates the status of the ARP binding relationship check function. The default value is 1."
			::= { hwVapProfileEntry 21 }

		 --1.3.6.1.4.1.2011.6.139.11.1.20.1.22
		hwVapOptinon82InsertSwitch OBJECT-TYPE
			SYNTAX INTEGER
				{
				disable(1) ,
				enable(2)
				}
			MAX-ACCESS read-write
			STATUS current
			DESCRIPTION 
				"This object indicates the status of the function of appending the Option 82 field to DHCP messages. The default value is 1."
			::= { hwVapProfileEntry 22 }

		 --1.3.6.1.4.1.2011.6.139.11.1.20.1.23
		hwVapOptinon82InsertRidFormat OBJECT-TYPE
			SYNTAX INTEGER
				{
				apMac(1),
				apMacSsid(2),
				userDefined(3)
				}
			MAX-ACCESS read-write
			STATUS current
			DESCRIPTION 
				"This object indicates the mode to append the Option 82 field to DHCP messages. The default value is 2."
			::= { hwVapProfileEntry 23 }

		 --1.3.6.1.4.1.2011.6.139.11.1.20.1.24
		hwVapDhcpTrustPort OBJECT-TYPE
			SYNTAX INTEGER
				{
				disable(1) ,
				enable(2)
				}
			MAX-ACCESS read-write
			STATUS current
			DESCRIPTION 
				"This object indicates the status of the radio interface DHCP trust function. The default value is 1."
			::= { hwVapProfileEntry 24 }

		 --1.3.6.1.4.1.2011.6.139.11.1.20.1.25
		hwVapNdTrustPort OBJECT-TYPE
			SYNTAX INTEGER
				{
				disable(1) ,
				enable(2)
				}
			MAX-ACCESS read-write
			STATUS current
			DESCRIPTION 
				"This object indicates the status of the radio interface ND trust function. The default value is 1."
			::= { hwVapProfileEntry 25 }

		 --1.3.6.1.4.1.2011.6.139.11.1.20.1.26
		hwVapSecurityProfile OBJECT-TYPE
			SYNTAX OCTET STRING (SIZE (1..35))
			MAX-ACCESS read-write
			STATUS current
			DESCRIPTION 
				"The object indicates the security profile that is bound to the VAP. The default value is default."
			::= { hwVapProfileEntry 26 }

		 --1.3.6.1.4.1.2011.6.139.11.1.20.1.27
		hwVapTrafficProfile OBJECT-TYPE
			SYNTAX OCTET STRING (SIZE (1..35))
			MAX-ACCESS read-write
			STATUS current
			DESCRIPTION 
				"The object indicates the traffic profile that is bound to the VAP. The default value is default."
			::= { hwVapProfileEntry 27 }

		 --1.3.6.1.4.1.2011.6.139.11.1.20.1.28
		hwVapSsidProfile OBJECT-TYPE
			SYNTAX OCTET STRING (SIZE (1..35))
			MAX-ACCESS read-write
			STATUS current
			DESCRIPTION 
				"The object indicates the SSID profile that is bound to the VAP. The default value is default."
			::= { hwVapProfileEntry 28 }

		 --1.3.6.1.4.1.2011.6.139.11.1.20.1.29
		hwVapAuthenticationProfile OBJECT-TYPE
			SYNTAX OCTET STRING (SIZE (0..35))
			MAX-ACCESS read-write
			STATUS current
			DESCRIPTION 
				"The object indicates the authentication profile that is bound to the VAP. The default value is default."
			::= { hwVapProfileEntry 29 }

		 --1.3.6.1.4.1.2011.6.139.11.1.20.1.30
		hwVapSacProfile OBJECT-TYPE
			SYNTAX OCTET STRING (SIZE (0..35))
			MAX-ACCESS read-write
			STATUS current
			DESCRIPTION 
				"The object indicates the SAC profile that is bound to the VAP."
			::= { hwVapProfileEntry 30 }

		 --1.3.6.1.4.1.2011.6.139.11.1.20.1.31
		hwVapProfileRowStatus OBJECT-TYPE
			SYNTAX RowStatus
			MAX-ACCESS read-write
			STATUS current
			DESCRIPTION 
				"This object indicates the row status of this table. ROWSTATUS_CREATEANDFLOW and ROWSTATUS_DESTROY are commonly used.?	ROWSTATUS_UNDEFINED: undefined?	ROWSTATUS_ACTIVE: active?	ROWSTATUS_NOTINSERVICE: notInService?	ROWSTATUS_NOTREADY: notReady?	ROWSTATUS_CREATEANDFLOW: createAndGo?	ROWSTATUS_CREATEANDWAIT: createAndWait?	ROWSTATUS_DESTROY: destroy."
			::= { hwVapProfileEntry 31 }

		
		-- 1.3.6.1.4.1.2011.6.139.11.1.20.1.32
		hwVapUserProfile OBJECT-TYPE
			SYNTAX OCTET STRING (SIZE (0..35))
			MAX-ACCESS read-write
			STATUS current
			DESCRIPTION
				"The object indicates the user profile that is bound to the VAP."
			::= { hwVapProfileEntry 32 }

		
		-- 1.3.6.1.4.1.2011.6.139.11.1.20.1.33
		hwVapHotspot2Profile OBJECT-TYPE
			SYNTAX OCTET STRING (SIZE (0..35))
			MAX-ACCESS read-write
			STATUS current
			DESCRIPTION
				"The object indicates the Hotspot2.0 profile that is bound to the VAP."
			::= { hwVapProfileEntry 33 }

		
		-- 1.3.6.1.4.1.2011.6.139.11.1.20.1.34
		hwSoftgreProfile OBJECT-TYPE
			SYNTAX OCTET STRING (SIZE (0..35))
			MAX-ACCESS read-write
			STATUS current
			DESCRIPTION
				"The object indicates the Softgre profile that is bound to the VAP."
			::= { hwVapProfileEntry 34 }
			
		 --1.3.6.1.4.1.2011.6.139.11.1.20.1.35
		hwVapOptinon82RidUserDefined OBJECT-TYPE
			SYNTAX OCTET STRING (SIZE (1..255))
			MAX-ACCESS read-write
			STATUS current
			DESCRIPTION 
				"Description."
			::= { hwVapProfileEntry 35 }

		 --1.3.6.1.4.1.2011.6.139.11.1.20.1.36
		hwVapOptinon82RidMacFormat OBJECT-TYPE
			SYNTAX INTEGER
				{
				default(0),
				normal(1) ,
				compact(2)
				}
			MAX-ACCESS read-write
			STATUS current
			DESCRIPTION 
				"Description."
			::= { hwVapProfileEntry 36 }
			
		 --1.3.6.1.4.1.2011.6.139.11.1.20.1.37
		hwVapOptinon82InsertCidFormat OBJECT-TYPE
			SYNTAX INTEGER
				{
				apMac(1),
				apMacSsid(2),
				userDefined(3)
				}
			MAX-ACCESS read-write
			STATUS current
			DESCRIPTION 
				"Description."
			::= { hwVapProfileEntry 37 }
			
			
		 --1.3.6.1.4.1.2011.6.139.11.1.20.1.38
		hwVapOptinon82CidUserDefined OBJECT-TYPE
			SYNTAX OCTET STRING (SIZE (1..255))
			MAX-ACCESS read-write
			STATUS current
			DESCRIPTION 
				"Description."
			::= { hwVapProfileEntry 38 }

		 --1.3.6.1.4.1.2011.6.139.11.1.20.1.39
		hwVapOptinon82CidMacFormat OBJECT-TYPE
			SYNTAX INTEGER
				{
				default(0),
				normal(1) ,
				compact(2)
				}
			MAX-ACCESS read-write
			STATUS current
			DESCRIPTION 
				"Description."
			::= { hwVapProfileEntry 39 }

                 --1.3.6.1.4.1.2011.6.139.11.1.20.1.40
		hwVapUccProfile OBJECT-TYPE
			SYNTAX OCTET STRING (SIZE (0..35))
			MAX-ACCESS read-write
			STATUS current
			DESCRIPTION 
				"The object indicates the UCC profile that is bound to the VAP."
			::= { hwVapProfileEntry 40 }
		
		-- 1.3.6.1.4.1.2011.6.139.11.1.20.1.41
		hwVapAntiAttackBroadcastFloodSwitch OBJECT-TYPE
			SYNTAX INTEGER
				{
				disable(1),
				enable(2)
				}
			MAX-ACCESS read-write
			STATUS current
			DESCRIPTION
				"This object indicates the status of the VAP anti-attack braoadcast flood function. The default value is 2."
			::= { hwVapProfileEntry 41 }
		
		-- 1.3.6.1.4.1.2011.6.139.11.1.20.1.42
		hwVapAntiAttackBroadcastFloodStaRateThreshold OBJECT-TYPE
			SYNTAX Unsigned32 (5..5000)
			MAX-ACCESS read-write
			STATUS current
			DESCRIPTION
				"This object indicates the anti-attack braoadcast flood sta-rate-threshold for the VAP. The default value is 50."
			::= { hwVapProfileEntry 42 }
			
		-- 1.3.6.1.4.1.2011.6.139.11.1.20.1.43
		hwVapAntiAttackBroadcastFloodBlacklistSwitch OBJECT-TYPE
			SYNTAX INTEGER
				{
				disable(1),
				enable(2)
				}
			MAX-ACCESS read-write
			STATUS current
			DESCRIPTION
				"This object indicates the status of the VAP anti-attack braoadcast flood blacklist function. The default value is 2."
			::= { hwVapProfileEntry 43 }
		
		--1.3.6.1.4.1.2011.6.139.11.1.21
		hwSsidProfileTable OBJECT-TYPE
			SYNTAX SEQUENCE OF HwSsidProfileEntry 
			MAX-ACCESS not-accessible
			STATUS current
			DESCRIPTION 
				"This table is used to configure and query SSID profile parameters."
			::= { hwWlanConfigObjects 21 }

		--1.3.6.1.4.1.2011.6.139.11.1.21.1
		hwSsidProfileEntry OBJECT-TYPE
			SYNTAX HwSsidProfileEntry 
			MAX-ACCESS not-accessible
			STATUS current
			DESCRIPTION 
				"The index of this table is hwSsidProfileName."
			INDEX { hwSsidProfileName }
			::= { hwSsidProfileTable 1 }


		HwSsidProfileEntry ::=
			SEQUENCE {				
				hwSsidProfileName
					OCTET STRING,
				hwSsidText
					OCTET STRING,
				hwSsidHide
					INTEGER,
				hwSsidAssocTimeout
					Unsigned32,
				hwSsidMaxStaNum
					Unsigned32,
				hwSsidLegacyStaSwitch
					INTEGER,
				hwSsidDtimInterval
					Unsigned32,
				hwSsidClientEdcaVoiceECWmax
					Unsigned32,
				hwSsidClientEdcaVoiceECWmin
					Unsigned32,
				hwSsidClientEdcaVoiceAIFSN
					Unsigned32,
				hwSsidClientEdcaVoiceTXOPLimit
					Unsigned32,
				hwSsidClientEdcaVideoECWmax
					Unsigned32,
				hwSsidClientEdcaVideoECWmin
					Unsigned32,
				hwSsidClientEdcaVideoAIFSN
					Unsigned32,
				hwSsidClientEdcaVideoTXOPLimit
					Unsigned32,
				hwSsidClientEdcaBeECWmax
					Unsigned32,
				hwSsidClientEdcaBeECWmin
					Unsigned32,
				hwSsidClientEdcaBeAIFSN
					Unsigned32,
				hwSsidClientEdcaBeTXOPLimit
					Unsigned32,
				hwSsidClientEdcaBkECWmax
					Unsigned32,
				hwSsidClientEdcaBkECWmin
					Unsigned32,
				hwSsidClientEdcaBkAIFSN
					Unsigned32,
				hwSsidClientEdcaBkTXOPLimit
					Unsigned32,
				hwSsidInboundCarCir
					Unsigned32,
				hwSsidInboundCarPir
					Unsigned32,
				hwSsidInboundCarCbs
					Unsigned32,
				hwSsidInboundCarPbs
					Unsigned32,
				hwSsidOutboundCarCir
					Unsigned32,
				hwSsidOutboundCarPir
					Unsigned32,
				hwSsidOutboundCarCbs
					Unsigned32,
				hwSsidOutboundCarPbs
					Unsigned32,
				hwSsidProfileRowStatus
					RowStatus,
				hwSsidHideWhileReachMaxSta
					INTEGER,
				hwSsidBeacon2gRate
					INTEGER,
				hwSsidBeacon5gRate
					INTEGER,
				hwSsidDenyBroadcastProbe
					INTEGER,
				hwSsidProbeResponseRetry
					Unsigned32,
				hwSsidUapsd
					INTEGER,
				hwSsidActiveDullClient
					INTEGER
			 }

		 --1.3.6.1.4.1.2011.6.139.11.1.21.1.1
		hwSsidProfileName OBJECT-TYPE
			SYNTAX OCTET STRING (SIZE (1..35))
			MAX-ACCESS not-accessible
			STATUS current
			DESCRIPTION 
				"This object indicates the name of a VAP profile. It is the index of the table."
			::= { hwSsidProfileEntry 1 }

		 --1.3.6.1.4.1.2011.6.139.11.1.21.1.2
		hwSsidText OBJECT-TYPE
			SYNTAX OCTET STRING (SIZE (1..32))
			MAX-ACCESS read-write
			STATUS current
			DESCRIPTION 
				"This object indicates the SSID character string. The default value is huawei-default."
			::= { hwSsidProfileEntry 2 }

		 --1.3.6.1.4.1.2011.6.139.11.1.21.1.3
		hwSsidHide OBJECT-TYPE
			SYNTAX INTEGER
				{
				disable(1) ,
				enable(2)
				}
			MAX-ACCESS read-write
			STATUS current
			DESCRIPTION 
				"This object indicates whether to enable SSID hiding. The default value is 1."
			::= { hwSsidProfileEntry 3 }

		 --1.3.6.1.4.1.2011.6.139.11.1.21.1.4
		hwSsidAssocTimeout OBJECT-TYPE
			SYNTAX Unsigned32 (1..30)
			MAX-ACCESS read-write
			STATUS current
			DESCRIPTION 
				"This object indicates the association timeout period of a user. The default value is 5 minutes."
			::= { hwSsidProfileEntry 4 }

		 --1.3.6.1.4.1.2011.6.139.11.1.21.1.5
		hwSsidMaxStaNum OBJECT-TYPE
			SYNTAX Unsigned32 (1..128)
			MAX-ACCESS read-write
			STATUS current
			DESCRIPTION 
				"The object indicates the number of access users on a VAP. The default value is 64."
			::= { hwSsidProfileEntry 5 }

		 --1.3.6.1.4.1.2011.6.139.11.1.21.1.6
		hwSsidLegacyStaSwitch OBJECT-TYPE
			SYNTAX INTEGER
				{
				disable(1) ,
				enable(2)
				}
			MAX-ACCESS read-write
			STATUS current
			DESCRIPTION 
				"This object indicates whether to allow access from legacy terminals. The default value is 2."
			::= { hwSsidProfileEntry 6 }

		 --1.3.6.1.4.1.2011.6.139.11.1.21.1.7
		hwSsidDtimInterval OBJECT-TYPE
			SYNTAX Unsigned32 (1..255)
			MAX-ACCESS read-write
			STATUS current
			DESCRIPTION 
				"This object indicates the DTIM interval. The default value is 3."
			::= { hwSsidProfileEntry 7 }

		 --1.3.6.1.4.1.2011.6.139.11.1.21.1.8
		hwSsidClientEdcaVoiceECWmax OBJECT-TYPE
			SYNTAX Unsigned32 (0..15)
			MAX-ACCESS read-write
			STATUS current
			DESCRIPTION 
				"This object indicates the ECWmax value, which determines the average avoidance time. The value of this object is the ECWmax value of the AC_VO queue on the station. The default value is 3."
			::= { hwSsidProfileEntry 8 }

		 --1.3.6.1.4.1.2011.6.139.11.1.21.1.9
		hwSsidClientEdcaVoiceECWmin OBJECT-TYPE
			SYNTAX Unsigned32 (0..15)
			MAX-ACCESS read-write
			STATUS current
			DESCRIPTION 
				"This object indicates the ECWmin value, which determines the average avoidance time. The value of this object is the ECWmin value of the AC_VO queue on the station. The default value is 2."
			::= { hwSsidProfileEntry 9 }

		 --1.3.6.1.4.1.2011.6.139.11.1.21.1.10
		hwSsidClientEdcaVoiceAIFSN OBJECT-TYPE
			SYNTAX Unsigned32 (1..15)
			MAX-ACCESS read-write
			STATUS current
			DESCRIPTION 
				"This object indicates the AIFSN value, which determines the idle waiting time. The value of this object is the AIFSN value of the AC_VO queue on the station. The default value is 2."
			::= { hwSsidProfileEntry 10 }

		 --1.3.6.1.4.1.2011.6.139.11.1.21.1.11
		hwSsidClientEdcaVoiceTXOPLimit OBJECT-TYPE
			SYNTAX Unsigned32 (0..255)
			MAX-ACCESS read-write
			STATUS current
			DESCRIPTION 
				"This object indicates the TXOPLimit value, which determines the time for occupying the channel. The value of this object is the TXOPLimit value of the AC_VO queue on the station. The default value is 47."
			::= { hwSsidProfileEntry 11 }

		 --1.3.6.1.4.1.2011.6.139.11.1.21.1.12
		hwSsidClientEdcaVideoECWmax OBJECT-TYPE
			SYNTAX Unsigned32 (0..15)
			MAX-ACCESS read-write
			STATUS current
			DESCRIPTION 
				"This object indicates the ECWmax value, which determines the average avoidance time. The value of this object is the ECWmax value of the AC_VI queue on the station. The default value is 4."
			::= { hwSsidProfileEntry 12 }

		 --1.3.6.1.4.1.2011.6.139.11.1.21.1.13
		hwSsidClientEdcaVideoECWmin OBJECT-TYPE
			SYNTAX Unsigned32 (0..15)
			MAX-ACCESS read-write
			STATUS current
			DESCRIPTION 
				"This object indicates the ECWmin value, which determines the average avoidance time. The value of this object is the ECWmin value of the AC_VI queue on the station. The default value is 3."
			::= { hwSsidProfileEntry 13 }

		 --1.3.6.1.4.1.2011.6.139.11.1.21.1.14
		hwSsidClientEdcaVideoAIFSN OBJECT-TYPE
			SYNTAX Unsigned32 (1..15)
			MAX-ACCESS read-write
			STATUS current
			DESCRIPTION 
				"This object indicates the AIFSN value, which determines the idle waiting time. The value of this object is the AIFSN value of the AC_VI queue on the station. The default value is 2."
			::= { hwSsidProfileEntry 14 }

		 --1.3.6.1.4.1.2011.6.139.11.1.21.1.15
		hwSsidClientEdcaVideoTXOPLimit OBJECT-TYPE
			SYNTAX Unsigned32 (0..255)
			MAX-ACCESS read-write
			STATUS current
			DESCRIPTION 
				"This object indicates the TXOPLimit value, which determines the time for occupying the channel. The value of this object is the TXOPLimit value of the AC_VI queue on the station. The default value is 94."
			::= { hwSsidProfileEntry 15 }

		 --1.3.6.1.4.1.2011.6.139.11.1.21.1.16
		hwSsidClientEdcaBeECWmax OBJECT-TYPE
			SYNTAX Unsigned32 (0..15)
			MAX-ACCESS read-write
			STATUS current
			DESCRIPTION 
				"This object indicates the ECWmax value, which determines the average avoidance time. The value of this object is the ECWmax value of the AC_BE queue on the station. The default value is 10."
			::= { hwSsidProfileEntry 16 }

		 --1.3.6.1.4.1.2011.6.139.11.1.21.1.17
		hwSsidClientEdcaBeECWmin OBJECT-TYPE
			SYNTAX Unsigned32 (0..15)
			MAX-ACCESS read-write
			STATUS current
			DESCRIPTION 
				"This object indicates the ECWmin value, which determines the average avoidance time. The value of this object is the ECWmin value of the AC_BE queue on the station. The default value is 4."
			::= { hwSsidProfileEntry 17 }

		 --1.3.6.1.4.1.2011.6.139.11.1.21.1.18
		hwSsidClientEdcaBeAIFSN OBJECT-TYPE
			SYNTAX Unsigned32 (1..15)
			MAX-ACCESS read-write
			STATUS current
			DESCRIPTION 
				"This object indicates the AIFSN value, which determines the idle waiting time. The value of this object is the AIFSN value of the AC_BE queue on the station. The default value is 3."
			::= { hwSsidProfileEntry 18 }

		 --1.3.6.1.4.1.2011.6.139.11.1.21.1.19
		hwSsidClientEdcaBeTXOPLimit OBJECT-TYPE
			SYNTAX Unsigned32 (0..255)
			MAX-ACCESS read-write
			STATUS current
			DESCRIPTION 
				"This object indicates the TXOPLimit value, which determines the time for occupying the channel. The value of this object is the TXOPLimit value of the AC_BE queue on the station. The default value is 0."
			::= { hwSsidProfileEntry 19 }

		 --1.3.6.1.4.1.2011.6.139.11.1.21.1.20
		hwSsidClientEdcaBkECWmax OBJECT-TYPE
			SYNTAX Unsigned32 (0..15)
			MAX-ACCESS read-write
			STATUS current
			DESCRIPTION 
				"This object indicates the ECWmax value, which determines the average avoidance time. The value of this object is the ECWmax value of the AC_BK queue on the station. The default value is 10."
			::= { hwSsidProfileEntry 20 }

		 --1.3.6.1.4.1.2011.6.139.11.1.21.1.21
		hwSsidClientEdcaBkECWmin OBJECT-TYPE
			SYNTAX Unsigned32 (0..15)
			MAX-ACCESS read-write
			STATUS current
			DESCRIPTION 
				"This object indicates the ECWmin value, which determines the average avoidance time. The value of this object is the ECWmin value of the AC_BK queue on the station. The default value is 4."
			::= { hwSsidProfileEntry 21 }

		 --1.3.6.1.4.1.2011.6.139.11.1.21.1.22
		hwSsidClientEdcaBkAIFSN OBJECT-TYPE
			SYNTAX Unsigned32 (1..15)
			MAX-ACCESS read-write
			STATUS current
			DESCRIPTION 
				"This object indicates the AIFSN value, which determines the idle waiting time. The value of this object is the AIFSN value of the AC_BK queue on the station. The default value is 7."
			::= { hwSsidProfileEntry 22 }

		 --1.3.6.1.4.1.2011.6.139.11.1.21.1.23
		hwSsidClientEdcaBkTXOPLimit OBJECT-TYPE
			SYNTAX Unsigned32 (0..255)
			MAX-ACCESS read-write
			STATUS current
			DESCRIPTION 
				"This object indicates the TXOPLimit value, which determines the time for occupying the channel. The value of this object is the TXOPLimit value of the AC_BK queue on the station. The default value is 0."
			::= { hwSsidProfileEntry 23 }

		 --1.3.6.1.4.1.2011.6.139.11.1.21.1.24
		hwSsidInboundCarCir OBJECT-TYPE
			SYNTAX Unsigned32 (0..4294967295)
			MAX-ACCESS read-write
			STATUS current
			DESCRIPTION 
				"This object indicates the inbound committed information rate (CIR) of the SSID. The default value is 0 kbit/s. Invalid value is 1 to 63."
			::= { hwSsidProfileEntry 24 }

		 --1.3.6.1.4.1.2011.6.139.11.1.21.1.25
		hwSsidInboundCarPir OBJECT-TYPE
			SYNTAX Unsigned32 (0..4294967295)
			MAX-ACCESS read-write
			STATUS current
			DESCRIPTION 
				"This object indicates the inbound peak information rate (PIR) of the SSID. The default value is 0 kbit/s. Invalid value is 1 to 63."
			::= { hwSsidProfileEntry 25 }

		 --1.3.6.1.4.1.2011.6.139.11.1.21.1.26
		hwSsidInboundCarCbs OBJECT-TYPE
			SYNTAX Unsigned32 (0..4294967295)
			MAX-ACCESS read-write
			STATUS current
			DESCRIPTION 
				"This object indicates the inbound committed burst size (CBS) of the SSID. The default value is 0 bytes. Invalid value is 1 to 1499."
			::= { hwSsidProfileEntry 26 }

		 --1.3.6.1.4.1.2011.6.139.11.1.21.1.27
		hwSsidInboundCarPbs OBJECT-TYPE
			SYNTAX Unsigned32 (0..4294967295)
			MAX-ACCESS read-write
			STATUS current
			DESCRIPTION 
				"This object indicates the inbound peak burst size (PBS) of the SSID. The default value is 0 bytes. Invalid value is 1 to 1499."
			::= { hwSsidProfileEntry 27 }

		 --1.3.6.1.4.1.2011.6.139.11.1.21.1.28
		hwSsidOutboundCarCir OBJECT-TYPE
			SYNTAX Unsigned32 (0..4294967295)
			MAX-ACCESS read-write
			STATUS current
			DESCRIPTION 
				"This object indicates the outbound committed information rate (CIR) of the SSID. The default value is 0 kbit/s. Invalid value is 1 to 63."
			::= { hwSsidProfileEntry 28 }

		 --1.3.6.1.4.1.2011.6.139.11.1.21.1.29
		hwSsidOutboundCarPir OBJECT-TYPE
			SYNTAX Unsigned32 (0..4294967295)
			MAX-ACCESS read-write
			STATUS current
			DESCRIPTION 
				"This object indicates the outbound peak information rate (PIR) of the SSID. The default value is 0 kbit/s. Invalid value is 1 to 63."
			::= { hwSsidProfileEntry 29 }

		 --1.3.6.1.4.1.2011.6.139.11.1.21.1.30
		hwSsidOutboundCarCbs OBJECT-TYPE
			SYNTAX Unsigned32 (0..4294967295)
			MAX-ACCESS read-write
			STATUS current
			DESCRIPTION 
				"This object indicates the outbound committed burst size (CBS) of the SSID. The default value is 0 bytes. Invalid value is 1 to 1499."
			::= { hwSsidProfileEntry 30 }

		 --1.3.6.1.4.1.2011.6.139.11.1.21.1.31
		hwSsidOutboundCarPbs OBJECT-TYPE
			SYNTAX Unsigned32 (0..4294967295)
			MAX-ACCESS read-write
			STATUS current
			DESCRIPTION 
				"This object indicates the outbound peak burst size (PBS) of the SSID. The default value is 0 bytes. Invalid value is 1 to 1499."
			::= { hwSsidProfileEntry 31 }

		 --1.3.6.1.4.1.2011.6.139.11.1.21.1.32
		hwSsidProfileRowStatus OBJECT-TYPE
			SYNTAX RowStatus
			MAX-ACCESS read-write
			STATUS current
			DESCRIPTION 
				"Description."
			::= { hwSsidProfileEntry 32 }

		-- 1.3.6.1.4.1.2011.6.139.11.1.21.1.33
		hwSsidHideWhileReachMaxSta OBJECT-TYPE
			SYNTAX INTEGER
				{
				disable(1),
				enable(2)
				}
			MAX-ACCESS read-write
			STATUS current
			DESCRIPTION
				"Description."
			::= { hwSsidProfileEntry 33 }
			
		
			
		 --1.3.6.1.4.1.2011.6.139.11.1.21.1.34
		hwSsidBeacon2gRate OBJECT-TYPE
			SYNTAX INTEGER
				{
				one(1),
				two(2),
				five(5),
				six(6),
				nine(9),
				eleven(11),
				twelve(12),
				eighteen(18),
				twentyfour(24),
				thirtysix(36),
				fortyeight (48),
				fiftyfour(54)
				}
			MAX-ACCESS read-write
			STATUS current
			DESCRIPTION 
				"Description."
			::= { hwSsidProfileEntry 34 }
			
		 --1.3.6.1.4.1.2011.6.139.11.1.21.1.35
		hwSsidBeacon5gRate OBJECT-TYPE
			SYNTAX INTEGER
				{
				six(6),
				nine(9),
				twelve(12),
				eighteen(18),
				twentyfour(24),
				thirtysix(36),
				fortyeight (48),
				fiftyfour(54)
				}
			MAX-ACCESS read-write
			STATUS current
			DESCRIPTION 
				"Description."
			::= { hwSsidProfileEntry 35 }
			
		 --1.3.6.1.4.1.2011.6.139.11.1.21.1.36
		hwSsidDenyBroadcastProbe OBJECT-TYPE
			SYNTAX INTEGER
				{
				disable(1) ,
				enable(2)
				}
			MAX-ACCESS read-write
			STATUS current
			DESCRIPTION 
				"Description."
			::= { hwSsidProfileEntry 36 }

		  --1.3.6.1.4.1.2011.6.139.11.1.21.1.37
		hwSsidProbeResponseRetry OBJECT-TYPE
			SYNTAX  Unsigned32 (0..3)
			MAX-ACCESS read-write
			STATUS current
			DESCRIPTION 
				"Description."
			::= { hwSsidProfileEntry 37 }


		
		-- 1.3.6.1.4.1.2011.6.139.11.1.21.1.38
		hwSsidUapsd OBJECT-TYPE
			SYNTAX INTEGER
				{
				disable(1),
				enable(2)
				}
			MAX-ACCESS read-write
			STATUS current
			DESCRIPTION
				"Description."
			::= { hwSsidProfileEntry 38 }

		
		-- 1.3.6.1.4.1.2011.6.139.11.1.21.1.39
		hwSsidActiveDullClient OBJECT-TYPE
			SYNTAX INTEGER
				{
				disable(1),
				enable(2)
				}
			MAX-ACCESS read-write
			STATUS current
			DESCRIPTION
				"Description."
			::= { hwSsidProfileEntry 39 }

		--1.3.6.1.4.1.2011.6.139.11.1.22
		hwSecurityProfileTable OBJECT-TYPE
			SYNTAX SEQUENCE OF HwSecurityProfileEntry 
			MAX-ACCESS not-accessible
			STATUS current
			DESCRIPTION 
				"This object indicates the row status of this table. ROWSTATUS_CREATEANDFLOW and ROWSTATUS_DESTROY are commonly used."
			::= { hwWlanConfigObjects 22 }

		--1.3.6.1.4.1.2011.6.139.11.1.22.1
		hwSecurityProfileEntry OBJECT-TYPE
			SYNTAX HwSecurityProfileEntry 
			MAX-ACCESS not-accessible
			STATUS current
			DESCRIPTION 
				"The index of this table is hwSecurityProfileName."
			INDEX { hwSecurityProfileName }
			::= { hwSecurityProfileTable 1 }


		HwSecurityProfileEntry ::=
			SEQUENCE {				
				hwSecurityProfileName
					OCTET STRING,
				hwSecurityPolicy
					INTEGER,
				hwSecurityWepEncrypt
					Unsigned32,
				hwSecurityWepPskMode
					Unsigned32,
				hwSecurityWepPsk1
					OCTET STRING,
				hwSecurityWepPsk2
					OCTET STRING,
				hwSecurityWepPsk3
					OCTET STRING,
				hwSecurityWepPsk4
					OCTET STRING,
				hwSecurityWepDefaultKeyId
					Unsigned32,
				hwSecurityWpaEncrypt
					INTEGER,
				hwSecurityWpaPskMode
					INTEGER,
				hwSecurityWpaPsk
					OCTET STRING,
				hwSecurityWpaPtkUpdateSwitch
					INTEGER,
				hwSecurityWpaPtkUpdateInterval
					Unsigned32,
				hwSecurityWapiPskMode
					INTEGER,
				hwSecurityWapiPsk
					OCTET STRING,
				hwSecurityWapiAsuIpAddress
					IpAddress,
				hwSecurityWapiIssuerCertFileName
					OCTET STRING,
				hwSecurityWapiAsuCertFileName
					OCTET STRING,
				hwSecurityWapiAcCertFileName
					OCTET STRING,
				hwSecurityWapiAcPrvKeyFileName
					OCTET STRING,
				hwSecurityWapiIssuerPfxPassword
					OCTET STRING,
				hwSecurityWapiAsuPfxPassword
					OCTET STRING,
				hwSecurityWapiAcPfxPassword
					OCTET STRING,
				hwSecurityWapiAcPrvKeyPassword
					OCTET STRING,
				hwSecurityWapiCertRetransCount
					Unsigned32,
				hwSecurityWapiBkThreshold
					Unsigned32,
				hwSecurityWapiBkLifetime
					Unsigned32,
				hwSecurityWapiUskUpdateMethod
					INTEGER,
				hwSecurityWapiMskUpdateMethod
					INTEGER,
				hwSecurityWapiUskUpdateInterval
					Unsigned32,
				hwSecurityWapiUskUpdatePackets
					Unsigned32,
				hwSecurityWapiUskRetansCount
					Unsigned32,
				hwSecurityWapiMskUpdateInterval
					Unsigned32,
				hwSecurityWapiMskUpdatePackets
					Unsigned32,
				hwSecurityWapiMskRetansCount
					Unsigned32,
				hwSecurityWapiSATimeout
					Unsigned32,
				hwSecurityPMF
					Unsigned32,
				hwSecurityProfileRowStatus
					RowStatus 
			 }

		 --1.3.6.1.4.1.2011.6.139.11.1.22.1.1
		hwSecurityProfileName OBJECT-TYPE
			SYNTAX OCTET STRING (SIZE (1..35))
			MAX-ACCESS not-accessible
			STATUS current
			DESCRIPTION 
				"This object indicates the name of a security profile. It is the index of the table."
			::= { hwSecurityProfileEntry 1 }

		 --1.3.6.1.4.1.2011.6.139.11.1.22.1.2
		hwSecurityPolicy OBJECT-TYPE
			SYNTAX INTEGER
				{
				wapiCert(1),
				wapiPsk(2),
				wpaDot1x(3),
				wpaPsk(4),
				wpa2Dot1x(5),
				wpa2Psk(6),
				wepShareKey(7),
				open(8),
				wpaWpa2Psk(9),
				wpaWpa2Dot1x(10),
				wepNoauth(11)
				}
			MAX-ACCESS read-write
			STATUS current
			DESCRIPTION 
				"This object indicates the air interface authentication policy. The default value is 1."
			::= { hwSecurityProfileEntry 2 }

		 --1.3.6.1.4.1.2011.6.139.11.1.22.1.3
		hwSecurityWepEncrypt OBJECT-TYPE
			SYNTAX Unsigned32 (0..65535)
			MAX-ACCESS read-write
			STATUS current
			DESCRIPTION 
				"This object indicates the WEP encryption algorithm. The default value is 1."
			::= { hwSecurityProfileEntry 3 }

		 --1.3.6.1.4.1.2011.6.139.11.1.22.1.4
		hwSecurityWepPskMode OBJECT-TYPE
			SYNTAX Unsigned32 (0..65535)
			MAX-ACCESS read-write
			STATUS current
			DESCRIPTION 
				"This object indicates that the WEP PSK mode is PassPhase or Hex. The default value is 1."
			::= { hwSecurityProfileEntry 4 }

		 --1.3.6.1.4.1.2011.6.139.11.1.22.1.5
		hwSecurityWepPsk1 OBJECT-TYPE
			SYNTAX OCTET STRING (SIZE (1..68))
			MAX-ACCESS read-write
			STATUS current
			DESCRIPTION 
				"This object indicates the WEP PSK1."
			::= { hwSecurityProfileEntry 5 }

		 --1.3.6.1.4.1.2011.6.139.11.1.22.1.6
		hwSecurityWepPsk2 OBJECT-TYPE
			SYNTAX OCTET STRING (SIZE (1..68))
			MAX-ACCESS read-write
			STATUS current
			DESCRIPTION 
				"This object indicates the WEP PSK2."
			::= { hwSecurityProfileEntry 6 }

		 --1.3.6.1.4.1.2011.6.139.11.1.22.1.7
		hwSecurityWepPsk3 OBJECT-TYPE
			SYNTAX OCTET STRING (SIZE (1..68))
			MAX-ACCESS read-write
			STATUS current
			DESCRIPTION 
				"This object indicates the WEP PSK3."
			::= { hwSecurityProfileEntry 7 }

		 --1.3.6.1.4.1.2011.6.139.11.1.22.1.8
		hwSecurityWepPsk4 OBJECT-TYPE
			SYNTAX OCTET STRING (SIZE (1..68))
			MAX-ACCESS read-write
			STATUS current
			DESCRIPTION 
				"This object indicates the WEP PSK4."
			::= { hwSecurityProfileEntry 8 }

		 --1.3.6.1.4.1.2011.6.139.11.1.22.1.9
		hwSecurityWepDefaultKeyId OBJECT-TYPE
			SYNTAX Unsigned32 (1..4)
			MAX-ACCESS read-write
			STATUS current
			DESCRIPTION 
				"This object indicates the default key ID for WEP. The default value is 1."
			::= { hwSecurityProfileEntry 9 }

		 --1.3.6.1.4.1.2011.6.139.11.1.22.1.10
		hwSecurityWpaEncrypt OBJECT-TYPE
			SYNTAX INTEGER
				{
				unknown(0),
				wpaAes(1),
				wpaTkip(2),
				wpaAesTkip(3)
				}
			MAX-ACCESS read-write
			STATUS current
			DESCRIPTION 
				"This object indicates the WPA/WPA2 encryption algorithm."
			::= { hwSecurityProfileEntry 10 }

		 --1.3.6.1.4.1.2011.6.139.11.1.22.1.11
		hwSecurityWpaPskMode OBJECT-TYPE
			SYNTAX INTEGER
				{
				pskPassphase(1),
				pskHex(2)
				}
			MAX-ACCESS read-write
			STATUS current
			DESCRIPTION 
				"This object indicates whether the WPA PSK mode is PassPhase or Hex."
			::= { hwSecurityProfileEntry 11 }

		 --1.3.6.1.4.1.2011.6.139.11.1.22.1.12
		hwSecurityWpaPsk OBJECT-TYPE
			SYNTAX OCTET STRING (SIZE (1..108))
			MAX-ACCESS read-write
			STATUS current
			DESCRIPTION 
				"This object indicates the WPA/WPA2 PSK."
			::= { hwSecurityProfileEntry 12 }

		 --1.3.6.1.4.1.2011.6.139.11.1.22.1.13
		hwSecurityWpaPtkUpdateSwitch OBJECT-TYPE
			SYNTAX INTEGER
				{
				disable(1) ,
				enable(2)
				}
			MAX-ACCESS read-write
			STATUS current
			DESCRIPTION 
				"This object indicates the status of WPA PTK update function. The default value is 1."
			::= { hwSecurityProfileEntry 13 }

		 --1.3.6.1.4.1.2011.6.139.11.1.22.1.14
		hwSecurityWpaPtkUpdateInterval OBJECT-TYPE
			SYNTAX Unsigned32 (30..86400)
			MAX-ACCESS read-write
			STATUS current
			DESCRIPTION 
				"This object indicates the WPA PTK update interval. The default value is 43200 seconds."
			::= { hwSecurityProfileEntry 14 }

		 --1.3.6.1.4.1.2011.6.139.11.1.22.1.15
		hwSecurityWapiPskMode OBJECT-TYPE
			SYNTAX INTEGER
				{
				pskPassphase(1),
				pskHex(2)
				}
			MAX-ACCESS read-write
			STATUS current
			DESCRIPTION 
				"This object indicates the WAPI PSK mode. The default value is 2."
			::= { hwSecurityProfileEntry 15 }

		 --1.3.6.1.4.1.2011.6.139.11.1.22.1.16
		hwSecurityWapiPsk OBJECT-TYPE
			SYNTAX OCTET STRING (SIZE (1..108))
			MAX-ACCESS read-write
			STATUS current
			DESCRIPTION 
				"This object indicates the WAPI PSK."
			::= { hwSecurityProfileEntry 16 }

		 --1.3.6.1.4.1.2011.6.139.11.1.22.1.17
		hwSecurityWapiAsuIpAddress OBJECT-TYPE
			SYNTAX IpAddress
			MAX-ACCESS read-write
			STATUS current
			DESCRIPTION 
				"The object indicates the IP address of the WAPI ASU."
			::= { hwSecurityProfileEntry 17 }

		 --1.3.6.1.4.1.2011.6.139.11.1.22.1.18
		hwSecurityWapiIssuerCertFileName OBJECT-TYPE
			SYNTAX OCTET STRING (SIZE (0..255))
			MAX-ACCESS read-write
			STATUS current
			DESCRIPTION 
				"This object indicates the certificate file name of the WAPI issuer."
			::= { hwSecurityProfileEntry 18 }

		 --1.3.6.1.4.1.2011.6.139.11.1.22.1.19
		hwSecurityWapiAsuCertFileName OBJECT-TYPE
			SYNTAX OCTET STRING (SIZE (0..255))
			MAX-ACCESS read-write
			STATUS current
			DESCRIPTION 
				"This object indicate the certificate file name of the WAPI ASU."
			::= { hwSecurityProfileEntry 19 }

		 --1.3.6.1.4.1.2011.6.139.11.1.22.1.20
		hwSecurityWapiAcCertFileName OBJECT-TYPE
			SYNTAX OCTET STRING (SIZE (0..255))
			MAX-ACCESS read-write
			STATUS current
			DESCRIPTION 
				"This object indicate the certificate file name of the WAPI AC."
			::= { hwSecurityProfileEntry 20 }

		 --1.3.6.1.4.1.2011.6.139.11.1.22.1.21
		hwSecurityWapiAcPrvKeyFileName OBJECT-TYPE
			SYNTAX OCTET STRING (SIZE (0..255))
			MAX-ACCESS read-write
			STATUS current
			DESCRIPTION 
				"This object indicates the private key file name of the WAPI AC."
			::= { hwSecurityProfileEntry 21 }

		 --1.3.6.1.4.1.2011.6.139.11.1.22.1.22
		hwSecurityWapiIssuerPfxPassword OBJECT-TYPE
			SYNTAX OCTET STRING (SIZE (0..68))
			MAX-ACCESS read-write
			STATUS current
			DESCRIPTION 
				"This object indicates the WAPI issuer certificate key."
			::= { hwSecurityProfileEntry 22 }

		 --1.3.6.1.4.1.2011.6.139.11.1.22.1.23
		hwSecurityWapiAsuPfxPassword OBJECT-TYPE
			SYNTAX OCTET STRING (SIZE (0..68))
			MAX-ACCESS read-write
			STATUS current
			DESCRIPTION 
				"This object indicates the WAPI ASU certificate key."
			::= { hwSecurityProfileEntry 23 }

		 --1.3.6.1.4.1.2011.6.139.11.1.22.1.24
		hwSecurityWapiAcPfxPassword OBJECT-TYPE
			SYNTAX OCTET STRING (SIZE (0..68))
			MAX-ACCESS read-write
			STATUS current
			DESCRIPTION 
				"This object indicates the WAPI AC certificate key."
			::= { hwSecurityProfileEntry 24 }

		 --1.3.6.1.4.1.2011.6.139.11.1.22.1.25
		hwSecurityWapiAcPrvKeyPassword OBJECT-TYPE
			SYNTAX OCTET STRING (SIZE (0..68))
			MAX-ACCESS read-write
			STATUS current
			DESCRIPTION 
				"This object indicates the key for reading the AC private key file."
			::= { hwSecurityProfileEntry 25 }

		 --1.3.6.1.4.1.2011.6.139.11.1.22.1.26
		hwSecurityWapiCertRetransCount OBJECT-TYPE
			SYNTAX Unsigned32 (1..10)
			MAX-ACCESS read-write
			STATUS current
			DESCRIPTION 
				"This object indicates the number of retransmissions of WAPI certificate authentication packets. The default value is 3."
			::= { hwSecurityProfileEntry 26 }

		 --1.3.6.1.4.1.2011.6.139.11.1.22.1.27
		hwSecurityWapiBkThreshold OBJECT-TYPE
			SYNTAX Unsigned32 (1..100)
			MAX-ACCESS read-write
			STATUS current
			DESCRIPTION 
				"This object indicates the WAPI BK lifetime percentage. The default value is 80."
			::= { hwSecurityProfileEntry 27 }

		 --1.3.6.1.4.1.2011.6.139.11.1.22.1.28
		hwSecurityWapiBkLifetime OBJECT-TYPE
			SYNTAX Unsigned32 (600..604800)
			MAX-ACCESS read-write
			STATUS current
			DESCRIPTION 
				"This object indicates the interval for updating the WAPI BK. The default value is 10000 seconds."
			::= { hwSecurityProfileEntry 28 }

		 --1.3.6.1.4.1.2011.6.139.11.1.22.1.29
		hwSecurityWapiUskUpdateMethod OBJECT-TYPE
			SYNTAX INTEGER
				{
				disabled(1) ,
				timeBased(2) ,
				packetBased(3) ,
				timepacketBased(4)
				}
			MAX-ACCESS read-write
			STATUS current
			DESCRIPTION 
				"This object indicates the WAPI USK update mode. The default value is 2."
			::= { hwSecurityProfileEntry 29 }

		 --1.3.6.1.4.1.2011.6.139.11.1.22.1.30
		hwSecurityWapiMskUpdateMethod OBJECT-TYPE
			SYNTAX INTEGER
				{
				disabled(1) ,
				timeBased(2) ,
				packetBased(3) ,
				timepacketBased(4)
				}
			MAX-ACCESS read-write
			STATUS current
			DESCRIPTION 
				"This object indicates the WAPI MSK update mode. The default value is 2."
			::= { hwSecurityProfileEntry 30 }

		 --1.3.6.1.4.1.2011.6.139.11.1.22.1.31
		hwSecurityWapiUskUpdateInterval OBJECT-TYPE
			SYNTAX Unsigned32 (600..604800)
			MAX-ACCESS read-write
			STATUS current
			DESCRIPTION 
				"This object indicates the time-based interval for updating the WAPI USK. The default value is 86400 seconds."
			::= { hwSecurityProfileEntry 31 }

		 --1.3.6.1.4.1.2011.6.139.11.1.22.1.32
		hwSecurityWapiUskUpdatePackets OBJECT-TYPE
			SYNTAX Unsigned32 (1..4200000)
			MAX-ACCESS read-write
			STATUS current
			DESCRIPTION 
				"This object indicates the number of packets that will trigger WAPI USK update. The default value is 10."
			::= { hwSecurityProfileEntry 32 }

		 --1.3.6.1.4.1.2011.6.139.11.1.22.1.33
		hwSecurityWapiUskRetansCount OBJECT-TYPE
			SYNTAX Unsigned32 (1..10)
			MAX-ACCESS read-write
			STATUS current
			DESCRIPTION 
				"This object indicates the maximum number of retransmissions of a WAPI USK negotiation packet. The default value is 3."
			::= { hwSecurityProfileEntry 33 }

		 --1.3.6.1.4.1.2011.6.139.11.1.22.1.34
		hwSecurityWapiMskUpdateInterval OBJECT-TYPE
			SYNTAX Unsigned32 (600..604800)
			MAX-ACCESS read-write
			STATUS current
			DESCRIPTION 
				"This object indicates the time-based interval for updating the WAPI MSK. The default value is 86400 seconds."
			::= { hwSecurityProfileEntry 34 }

		 --1.3.6.1.4.1.2011.6.139.11.1.22.1.35
		hwSecurityWapiMskUpdatePackets OBJECT-TYPE
			SYNTAX Unsigned32 (1..4200000)
			MAX-ACCESS read-write
			STATUS current
			DESCRIPTION 
				"This object indicates the number of packets that will trigger WAPI MSK update. The default value is 10."
			::= { hwSecurityProfileEntry 35 }

		 --1.3.6.1.4.1.2011.6.139.11.1.22.1.36
		hwSecurityWapiMskRetansCount OBJECT-TYPE
			SYNTAX Unsigned32 (1..10)
			MAX-ACCESS read-write
			STATUS current
			DESCRIPTION 
				"This object indicates the maximum number of retransmissions of a WAPI MSK negotiation packet. The default value is 3."
			::= { hwSecurityProfileEntry 36 }

		 --1.3.6.1.4.1.2011.6.139.11.1.22.1.37
		hwSecurityWapiSATimeout OBJECT-TYPE
			SYNTAX Unsigned32 (1..255)
			MAX-ACCESS read-write
			STATUS current
			DESCRIPTION 
				"This object indicates the timeout period of a WAPI-based security association (SA). The default value is 60 seconds."
			::= { hwSecurityProfileEntry 37 }

		 --1.3.6.1.4.1.2011.6.139.11.1.22.1.38
		hwSecurityPMF OBJECT-TYPE
			SYNTAX Unsigned32 (1..3)
			MAX-ACCESS read-write
			STATUS current
			DESCRIPTION
				"This object indicates the status of the PMF function. The default value is 1."
			::= { hwSecurityProfileEntry 38 }
		hwSecurityProfileRowStatus OBJECT-TYPE
			SYNTAX RowStatus
			MAX-ACCESS read-write
			STATUS current
			DESCRIPTION 
				"This object indicates the row status of this table. ROWSTATUS_CREATEANDFLOW and ROWSTATUS_DESTROY are commonly used."
			::= { hwSecurityProfileEntry 39 }

		--1.3.6.1.4.1.2011.6.139.11.1.23
		hwAPTrafficProfileTable OBJECT-TYPE
			SYNTAX SEQUENCE OF HwAPTrafficProfileEntry 
			MAX-ACCESS not-accessible
			STATUS current
			DESCRIPTION 
				"This table is used to configure and query traffic profile parameters."
			::= { hwWlanConfigObjects 23 }

		--1.3.6.1.4.1.2011.6.139.11.1.23.1
		hwAPTrafficProfileEntry OBJECT-TYPE
			SYNTAX HwAPTrafficProfileEntry 
			MAX-ACCESS not-accessible
			STATUS current
			DESCRIPTION 
				"The index of this table is hwAPTrafficProfileName."
			INDEX { hwAPTrafficProfileName }
			::= { hwAPTrafficProfileTable 1 }


		HwAPTrafficProfileEntry ::=
			SEQUENCE {				
				hwAPTrafficProfileName
					OCTET STRING,
				hwAPTrafficProfilePriorityMapDnTrustMode
					INTEGER,
				hwAPTrafficProfilePriorityDscpDnMap80211e
					OCTET STRING,
				hwAPTrafficProfilePriority80211eUpMapDscp
					OCTET STRING,
				hwAPTrafficProfileUserIsolate
					INTEGER,
				hwAPTrafficProfileRateLimitClientUp
					Unsigned32,
				hwAPTrafficProfileRateLimitClientDn
					Unsigned32,
				hwAPTrafficProfileRateLimitVapUp
					Unsigned32,
				hwAPTrafficProfileRateLimitVapDn
					Unsigned32,
				hwAPTrafficProfileMldSnooping
					INTEGER,
				hwAPTrafficProfileIGMPSnooping
					INTEGER,
				hwAPTrafficProfileIGMPSnoopingReportSuppress
					INTEGER,
				hwAPTrafficProfileMcToUc
					INTEGER,
				hwAPTrafficProfileOptimizeSuppressionBc
					Unsigned32,
				hwAPTrafficProfileOptimizeSuppressionUc
					Unsigned32,
				hwAPTrafficProfileOptimizeSuppressionMc
					Unsigned32,
				hwAPTrafficProfileOptimizeTCPAdjustMSS
					Unsigned32,
				hwAPTrafficProfileOptimizeProxyARP
					INTEGER,
				hwAPTrafficProfileOptimizeProxyND
					INTEGER,
				hwAPTrafficProfileOptimizeUcSendARP
					INTEGER,
				hwAPTrafficProfileOptimizeUcSendND
					INTEGER,
				hwAPTrafficProfileOptimizeUcSendDHCP
					INTEGER,
				hwAPTrafficProfileOptimizeBcMcDenyAll
					INTEGER,
				hwAPTrafficProfileOptimizeStaBridgeForward
					INTEGER,
				hwAPTrafficProfileRowStatus
					RowStatus,
				hwAPTrafficProfilePriorityMapUpTrustMode
					INTEGER,
				hwAPTrafficProfilePriorityDscpUpMapDscp
					OCTET STRING
			 }

		 --1.3.6.1.4.1.2011.6.139.11.1.23.1.1
		hwAPTrafficProfileName OBJECT-TYPE
			SYNTAX OCTET STRING (SIZE (1..35))
			MAX-ACCESS not-accessible
			STATUS current
			DESCRIPTION 
				"This object indicates the name of a traffic profile."
			::= { hwAPTrafficProfileEntry 1 }

		 --1.3.6.1.4.1.2011.6.139.11.1.23.1.2
		hwAPTrafficProfilePriorityMapDnTrustMode OBJECT-TYPE
			SYNTAX INTEGER
				{
				trustDSCP(1),
				trust8021P(2)
				}
			MAX-ACCESS read-write
			STATUS current
			DESCRIPTION 
				"This object indicates the downstream service priority mapping mode. The default value is 1."
			::= { hwAPTrafficProfileEntry 2 }

		 --1.3.6.1.4.1.2011.6.139.11.1.23.1.3
		hwAPTrafficProfilePriorityDscpDnMap80211e OBJECT-TYPE
			SYNTAX OCTET STRING (SIZE (1..256))
			MAX-ACCESS read-write
			STATUS current
			DESCRIPTION 
				"This object indicates the mapping relationship between 802.1p priorities of 802.3 packets and user priorities of 802.11 packets when data packets are sent to a downstream AP. DSCP values range from 0 to 63 and 802.11e priorities range from 0 to 7. Two mapped data are separated by a comma."
			::= { hwAPTrafficProfileEntry 3 }

		 --1.3.6.1.4.1.2011.6.139.11.1.23.1.4
		hwAPTrafficProfilePriority80211eUpMapDscp OBJECT-TYPE
			SYNTAX OCTET STRING (SIZE (1..256))
			MAX-ACCESS read-write
			STATUS current
			DESCRIPTION 
				"This object indicates the tunnel priority mappings when data packets are sent from APs to an AC. DSCP values range from 0 to 63 and 802.11e priorities range from 0 to 7. Two mapped data are separated by a comma."
			::= { hwAPTrafficProfileEntry 4 }

		 --1.3.6.1.4.1.2011.6.139.11.1.23.1.5
		hwAPTrafficProfileUserIsolate OBJECT-TYPE
			SYNTAX INTEGER
				{
				disable(1),
				l3Isolate(2),
				l2Isolate(3)
				}
			MAX-ACCESS read-write
			STATUS current
			DESCRIPTION 
				"This object indicates the user isolation mode. The default value is 1."
			::= { hwAPTrafficProfileEntry 5 }

		 --1.3.6.1.4.1.2011.6.139.11.1.23.1.6
		hwAPTrafficProfileRateLimitClientUp OBJECT-TYPE
			SYNTAX Unsigned32 (64..4294967295)
			MAX-ACCESS read-write
			STATUS current
			DESCRIPTION 
				"This object indicates the STA's uplink rate limit. The default value is 0xFFFFFFFF. It is expressed in kbit/s."
			::= { hwAPTrafficProfileEntry 6 }

		 --1.3.6.1.4.1.2011.6.139.11.1.23.1.7
		hwAPTrafficProfileRateLimitClientDn OBJECT-TYPE
			SYNTAX Unsigned32 (64..4294967295)
			MAX-ACCESS read-write
			STATUS current
			DESCRIPTION 
				"This object indicates the STA's downlink rate limit. The default value is 0xFFFFFFFF. It is expressed in kbit/s."
			::= { hwAPTrafficProfileEntry 7 }

		 --1.3.6.1.4.1.2011.6.139.11.1.23.1.8
		hwAPTrafficProfileRateLimitVapUp OBJECT-TYPE
			SYNTAX Unsigned32 (64..4294967295)
			MAX-ACCESS read-write
			STATUS current
			DESCRIPTION 
				"This object indicates the VAP's uplink rate limit. The default value is 0xFFFFFFFF. It is expressed in kbit/s."
			::= { hwAPTrafficProfileEntry 8 }

		 --1.3.6.1.4.1.2011.6.139.11.1.23.1.9
		hwAPTrafficProfileRateLimitVapDn OBJECT-TYPE
			SYNTAX Unsigned32 (64..4294967295)
			MAX-ACCESS read-write
			STATUS current
			DESCRIPTION 
				"This object indicates the VAP's downlink rate limit. The default value is 0xFFFFFFFF. It is expressed in kbit/s."
			::= { hwAPTrafficProfileEntry 9 }

		 --1.3.6.1.4.1.2011.6.139.11.1.23.1.10
		hwAPTrafficProfileMldSnooping OBJECT-TYPE
			SYNTAX INTEGER
				{
				disable(1) ,
				enable(2)
				}
			MAX-ACCESS read-write
			STATUS current
			DESCRIPTION 
				"This object indicates the status of the MLD snooping function. The default value is 1."
			::= { hwAPTrafficProfileEntry 10 }

		 --1.3.6.1.4.1.2011.6.139.11.1.23.1.11
		hwAPTrafficProfileIGMPSnooping OBJECT-TYPE
			SYNTAX INTEGER
				{
				disable(1) ,
				enable(2)
				}
			MAX-ACCESS read-write
			STATUS current
			DESCRIPTION 
				"This object indicates the status of the IGMP snooping function. The default value is 1."
			::= { hwAPTrafficProfileEntry 11 }

		 --1.3.6.1.4.1.2011.6.139.11.1.23.1.12
		hwAPTrafficProfileIGMPSnoopingReportSuppress OBJECT-TYPE
			SYNTAX INTEGER
				{
				disable(1) ,
				enable(2)
				}
			MAX-ACCESS read-write
			STATUS current
			DESCRIPTION 
				"This object indicates the status of the IGMP snooping report suppression function. The default value is 1."
			::= { hwAPTrafficProfileEntry 12 }

		 --1.3.6.1.4.1.2011.6.139.11.1.23.1.13
		hwAPTrafficProfileMcToUc OBJECT-TYPE
			SYNTAX INTEGER
				{
				disable(1) ,
				enable(2)
				}
			MAX-ACCESS read-write
			STATUS current
			DESCRIPTION 
				"This object indicates the status of the function of converting multicast to unicast. The default value is 1."
			::= { hwAPTrafficProfileEntry 13 }

		 --1.3.6.1.4.1.2011.6.139.11.1.23.1.14
		hwAPTrafficProfileOptimizeSuppressionBc OBJECT-TYPE
			SYNTAX Unsigned32 (0..14881000|4294967295)
			MAX-ACCESS read-write
			STATUS current
			DESCRIPTION 
				"This object indicates the information about broadcast storm suppression. The unit is pps. The default value is 0xFFFFFFFF, indicating that the broadcast storm suppression is not enabled."
			::= { hwAPTrafficProfileEntry 14 }

		 --1.3.6.1.4.1.2011.6.139.11.1.23.1.15
		hwAPTrafficProfileOptimizeSuppressionUc OBJECT-TYPE
			SYNTAX Unsigned32 (0..14881000|4294967295)
			MAX-ACCESS read-write
			STATUS current
			DESCRIPTION 
				"This object indicates the information about unknown unicast storm suppression. The unit is pps. The default value is 0xFFFFFFFF, indicating that the broadcast storm suppression is not enabled."
			::= { hwAPTrafficProfileEntry 15 }

		 --1.3.6.1.4.1.2011.6.139.11.1.23.1.16
		hwAPTrafficProfileOptimizeSuppressionMc OBJECT-TYPE
			SYNTAX Unsigned32 (0..14881000|4294967295)
			MAX-ACCESS read-write
			STATUS current
			DESCRIPTION 
				"This object indicates the information about multicast storm suppression. The unit is pps. The default value is 0xFFFFFFFF, indicating that the broadcast storm suppression is not enabled."
			::= { hwAPTrafficProfileEntry 16 }

		 --1.3.6.1.4.1.2011.6.139.11.1.23.1.17
		hwAPTrafficProfileOptimizeTCPAdjustMSS OBJECT-TYPE
			SYNTAX Unsigned32 (128..2048|4294967295)
			MAX-ACCESS read-write
			STATUS current
			DESCRIPTION 
				"This object indicates the information about the automatic MSS adjustment. The default value is 0xFFFFFFFF, indicating that this function is not enabled."
			::= { hwAPTrafficProfileEntry 17 }

		 --1.3.6.1.4.1.2011.6.139.11.1.23.1.18
		hwAPTrafficProfileOptimizeProxyARP OBJECT-TYPE
			SYNTAX INTEGER
				{
				disable(1) ,
				enable(2)
				}
			MAX-ACCESS read-write
			STATUS current
			DESCRIPTION 
				"This object indicates the status of the ARP proxy function. The default value is 1."
			::= { hwAPTrafficProfileEntry 18 }

		 --1.3.6.1.4.1.2011.6.139.11.1.23.1.19
		hwAPTrafficProfileOptimizeProxyND OBJECT-TYPE
			SYNTAX INTEGER
				{
				disable(1) ,
				enable(2)
				}
			MAX-ACCESS read-write
			STATUS current
			DESCRIPTION 
				"This object indicates the status of the ND proxy function. The default value is 1."
			::= { hwAPTrafficProfileEntry 19 }

		 --1.3.6.1.4.1.2011.6.139.11.1.23.1.20
		hwAPTrafficProfileOptimizeUcSendARP OBJECT-TYPE
			SYNTAX INTEGER
				{
				disable(1) ,
				enable(2)
				}
			MAX-ACCESS read-write
			STATUS current
			DESCRIPTION 
				"This object indicates the status of the unicast ARP function. The default value is 2."
			::= { hwAPTrafficProfileEntry 20 }

		 --1.3.6.1.4.1.2011.6.139.11.1.23.1.21
		hwAPTrafficProfileOptimizeUcSendND OBJECT-TYPE
			SYNTAX INTEGER
				{
				disable(1) ,
				enable(2)
				}
			MAX-ACCESS read-write
			STATUS current
			DESCRIPTION 
				"This object indicates the status of the unicast ND function. The default value is 2."
			::= { hwAPTrafficProfileEntry 21 }

		 --1.3.6.1.4.1.2011.6.139.11.1.23.1.22
		hwAPTrafficProfileOptimizeUcSendDHCP OBJECT-TYPE
			SYNTAX INTEGER
				{
				disable(1) ,
				enable(2)
				}
			MAX-ACCESS read-write
			STATUS current
			DESCRIPTION 
				"This object indicates the status of the unicast DHCP function. The default value is 1."
			::= { hwAPTrafficProfileEntry 22 }

		 --1.3.6.1.4.1.2011.6.139.11.1.23.1.23
		hwAPTrafficProfileOptimizeBcMcDenyAll OBJECT-TYPE
			SYNTAX INTEGER
				{
				disable(1) ,
				enable(2)
				}
			MAX-ACCESS read-write
			STATUS current
			DESCRIPTION 
				"After this function is enabled, other multicast packets, except for proxy response packets and multicast packets converted to unicast packets, are discarded. The default value is 1."
			::= { hwAPTrafficProfileEntry 23 }

		 --1.3.6.1.4.1.2011.6.139.11.1.23.1.24
		hwAPTrafficProfileOptimizeStaBridgeForward OBJECT-TYPE
			SYNTAX INTEGER
				{
				disable(1) ,
				enable(2)
				}
			MAX-ACCESS read-write
			STATUS current
			DESCRIPTION 
				"This object indicates the status of the STA bridge forwarding function. The default value is 2."
			::= { hwAPTrafficProfileEntry 24 }

		
		-- 1.3.6.1.4.1.2011.6.139.11.1.23.1.25
		hwAPTrafficProfileRowStatus OBJECT-TYPE
			SYNTAX RowStatus
			MAX-ACCESS read-create
			STATUS current
			DESCRIPTION
				"This object indicates the row status of this table. ROWSTATUS_CREATEANDFLOW and ROWSTATUS_DESTROY are commonly used."
			::= { hwAPTrafficProfileEntry 25 }

		
		-- 1.3.6.1.4.1.2011.6.139.11.1.23.1.26
		hwAPTrafficProfilePriorityMapUpTrustMode OBJECT-TYPE
			SYNTAX INTEGER
				{
				trust80211e(1),
				trustdscp(2)
				}
			MAX-ACCESS read-write
			STATUS current
			DESCRIPTION
				"This object indicates the tunnel priority mapping mode."
			::= { hwAPTrafficProfileEntry 26 }

		
		-- 1.3.6.1.4.1.2011.6.139.11.1.23.1.27
		hwAPTrafficProfilePriorityDscpUpMapDscp OBJECT-TYPE
			SYNTAX OCTET STRING (SIZE (1..256))
			MAX-ACCESS read-write
			STATUS current
			DESCRIPTION
				"This object indicates the mapping relationship between DSCP and DSCP. DSCP values range from 0 to 63. Two mapped data are separated by a comma."
			::= { hwAPTrafficProfileEntry 27 }

		--1.3.6.1.4.1.2011.6.139.11.1.24
		hwAPTrafficProfileFilterTable OBJECT-TYPE
			SYNTAX SEQUENCE OF HwAPTrafficProfileFilterEntry 
			MAX-ACCESS not-accessible
			STATUS current
			DESCRIPTION 
				"This table is used to configure QoS filter information."
			::= { hwWlanConfigObjects 24 }

		--1.3.6.1.4.1.2011.6.139.11.1.24.1
		hwAPTrafficProfileFilterEntry OBJECT-TYPE
			SYNTAX HwAPTrafficProfileFilterEntry 
			MAX-ACCESS not-accessible
			STATUS current
			DESCRIPTION 
				"The indexes of this table are hwAPTrafficProfileName, hwAPTrafficProfileFilterType, and hwAPTrafficProfileFilterDirection."
			INDEX { hwAPTrafficProfileName, hwAPTrafficProfileFilterType,hwAPTrafficProfileFilterDirection  }
			::= { hwAPTrafficProfileFilterTable 1 }


		HwAPTrafficProfileFilterEntry ::=
			SEQUENCE {				
				hwAPTrafficProfileFilterDirection
					INTEGER,
				hwAPTrafficProfileFilterType
					INTEGER,
				hwAPTrafficProfileFilterACLID
					Integer32,
				hwAPTrafficProfileFilterRowStatus
					RowStatus 
			 }

		 --1.3.6.1.4.1.2011.6.139.11.1.24.1.1
		hwAPTrafficProfileFilterDirection OBJECT-TYPE
			SYNTAX INTEGER
				{
				inbound(1),
				outbound(2)
				}
			MAX-ACCESS not-accessible
			STATUS current
			DESCRIPTION 
				"This object indicates the ACL rule direction for packet filtering in a traffic profile. This parameter has no default value."
			::= { hwAPTrafficProfileFilterEntry 1 }

		 --1.3.6.1.4.1.2011.6.139.11.1.24.1.2
		hwAPTrafficProfileFilterType OBJECT-TYPE
			SYNTAX INTEGER
				{
				ipv4(1),
				ipv6(2)
				}
			MAX-ACCESS not-accessible
			STATUS current
			DESCRIPTION 
				"This object indicates the ACL rule type for packet filtering in a traffic profile. This parameter has no default value."
			::= { hwAPTrafficProfileFilterEntry 2 }

		 --1.3.6.1.4.1.2011.6.139.11.1.24.1.3
		hwAPTrafficProfileFilterACLID OBJECT-TYPE
			SYNTAX Integer32 (3000..3031|6000..6031)
			MAX-ACCESS read-write
			STATUS current
			DESCRIPTION 
				"This object indicates the ACL rule for packet filtering in a traffic profile."
			::= { hwAPTrafficProfileFilterEntry 3 }

		 --1.3.6.1.4.1.2011.6.139.11.1.24.1.4
		hwAPTrafficProfileFilterRowStatus OBJECT-TYPE
			SYNTAX RowStatus
			MAX-ACCESS read-create
			STATUS current
			DESCRIPTION 
				"This object indicates the row status of this table. ROWSTATUS_CREATEANDFLOW and ROWSTATUS_DESTROY are commonly used."
			::= { hwAPTrafficProfileFilterEntry 4 }

		--1.3.6.1.4.1.2011.6.139.11.1.25
		hwWlanVlanPoolTable OBJECT-TYPE
			SYNTAX SEQUENCE OF HwWlanVlanPoolEntry 
			MAX-ACCESS not-accessible
			STATUS current
			DESCRIPTION 
				"This table is used to configure VLAN pools."
			::= { hwWlanConfigObjects 25 }

		--1.3.6.1.4.1.2011.6.139.11.1.25.1
		hwWlanVlanPoolEntry OBJECT-TYPE
			SYNTAX HwWlanVlanPoolEntry 
			MAX-ACCESS not-accessible
			STATUS current
			DESCRIPTION 
				"The index of this table is hwVlanPoolName."
			INDEX { hwVlanPoolName }
			::= { hwWlanVlanPoolTable 1 }


		HwWlanVlanPoolEntry ::=
			SEQUENCE {				
				hwVlanPoolName
					OCTET STRING,
				hwVlanPoolVlanlist
					OCTET STRING,
				hwVlanPoolAssignMethod
					INTEGER,
				hwVlanPoolRowStatus
					RowStatus 
			 }

		 --1.3.6.1.4.1.2011.6.139.11.1.25.1.1
		hwVlanPoolName OBJECT-TYPE
			SYNTAX OCTET STRING (SIZE (1..31))
			MAX-ACCESS not-accessible
			STATUS current
			DESCRIPTION 
				"This object indicates the VLAN pool name. It is the index of the table."
			::= { hwWlanVlanPoolEntry 1 }

		 --1.3.6.1.4.1.2011.6.139.11.1.25.1.2
		hwVlanPoolVlanlist OBJECT-TYPE
			SYNTAX OCTET STRING (SIZE (0..640))
			MAX-ACCESS read-write
			STATUS current
			DESCRIPTION 
				"This object indicates the VLAN list."
			::= { hwWlanVlanPoolEntry 2 }

		 --1.3.6.1.4.1.2011.6.139.11.1.25.1.3
		hwVlanPoolAssignMethod OBJECT-TYPE
			SYNTAX INTEGER
				{
				hash(1),
				even(2)
				}
			MAX-ACCESS read-write
			STATUS current
			DESCRIPTION 
				"This object indicates the VLAN pool allocation algorithm. The default value is 1."
			::= { hwWlanVlanPoolEntry 3 }

		 --1.3.6.1.4.1.2011.6.139.11.1.25.1.4
		hwVlanPoolRowStatus OBJECT-TYPE
			SYNTAX RowStatus
			MAX-ACCESS read-write
			STATUS current
			DESCRIPTION 
				"This object indicates the row status of this table. ROWSTATUS_CREATEANDFLOW and ROWSTATUS_DESTROY are commonly used."
			::= { hwWlanVlanPoolEntry 4 }

		--1.3.6.1.4.1.2011.6.139.11.1.26
		hwWlanStaWhitelistConfig OBJECT IDENTIFIER ::= { hwWlanConfigObjects 26 }
		hwWlanStaWhitelistProfileTable OBJECT-TYPE
			SYNTAX SEQUENCE OF HwWlanStaWhitelistProfileEntry
			MAX-ACCESS not-accessible
			STATUS current
			DESCRIPTION 
				"This table is used to create STA whitelist profiles."
			::= { hwWlanStaWhitelistConfig 1 }

		
		-- 1.3.6.1.4.1.2011.6.139.11.1.26.1.1
		hwWlanStaWhitelistProfileEntry OBJECT-TYPE
			SYNTAX HwWlanStaWhitelistProfileEntry
			MAX-ACCESS not-accessible
			STATUS current
			DESCRIPTION 
				"The index of this table is hwWlanStaWhitelistProfileName."
			INDEX { hwWlanStaWhitelistProfileName }
			::= { hwWlanStaWhitelistProfileTable 1 }

		
		HwWlanStaWhitelistProfileEntry ::=
			SEQUENCE { 
				hwWlanStaWhitelistProfileName
					OCTET STRING,
				hwWlanStaWhitelistProfileRowStatus
					RowStatus
			 }

		-- 1.3.6.1.4.1.2011.6.139.11.1.26.1.1.1
		hwWlanStaWhitelistProfileName OBJECT-TYPE
			SYNTAX OCTET STRING (SIZE (1..35))
			MAX-ACCESS not-accessible
			STATUS current
			DESCRIPTION 
				"This object indicates the name of a STA whitelist profile. It is the index of the table."
			::= { hwWlanStaWhitelistProfileEntry 1 }

		
		-- 1.3.6.1.4.1.2011.6.139.11.1.26.1.1.2
		hwWlanStaWhitelistProfileRowStatus OBJECT-TYPE
			SYNTAX RowStatus
			MAX-ACCESS read-write
			STATUS current
			DESCRIPTION
				"This object indicates the row status of this table."
			::= { hwWlanStaWhitelistProfileEntry 2 }

		
		-- 1.3.6.1.4.1.2011.6.139.11.1.26.2
		hwWlanStaWhitelistProfileConfigTable OBJECT-TYPE
			SYNTAX SEQUENCE OF HwWlanStaWhitelistProfileConfigEntry
			MAX-ACCESS not-accessible
			STATUS current
			DESCRIPTION
				"This table is used to configure STA whitelist profiles."
			::= { hwWlanStaWhitelistConfig 2 }

		
		-- 1.3.6.1.4.1.2011.6.139.11.1.26.2.1
		hwWlanStaWhitelistProfileConfigEntry OBJECT-TYPE
			SYNTAX HwWlanStaWhitelistProfileConfigEntry
			MAX-ACCESS not-accessible
			STATUS current
			DESCRIPTION
				"The indexes of this table are hwWlanStaWhitelistProfileName and hwWlanStaWhitelistStaMac."
			INDEX { hwWlanStaWhitelistStaMac, hwWlanStaWhitelistProfileName }
			::= { hwWlanStaWhitelistProfileConfigTable 1 }

		
		HwWlanStaWhitelistProfileConfigEntry ::=
			SEQUENCE { 
				hwWlanStaWhitelistStaMac
					MacAddress,
				hwWlanStaWhitelistRowStatus
					RowStatus
			 }

		-- 1.3.6.1.4.1.2011.6.139.11.1.26.2.1.1
		hwWlanStaWhitelistStaMac OBJECT-TYPE
			SYNTAX MacAddress
			MAX-ACCESS not-accessible
			STATUS current
			DESCRIPTION
				"This object indicates the whitelist."
			::= { hwWlanStaWhitelistProfileConfigEntry 1 }

		
		-- 1.3.6.1.4.1.2011.6.139.11.1.26.2.1.2
		hwWlanStaWhitelistRowStatus OBJECT-TYPE
			SYNTAX RowStatus
			MAX-ACCESS read-write
			STATUS current
			DESCRIPTION
				"This object indicates the row status of this table. ROWSTATUS_CREATEANDFLOW and ROWSTATUS_DESTROY are commonly used."
			::= { hwWlanStaWhitelistProfileConfigEntry 2 }

		
		-- 1.3.6.1.4.1.2011.6.139.11.1.27
		hwWlanStaBlacklistConfig OBJECT IDENTIFIER ::= { hwWlanConfigObjects 27 }

		
		-- 1.3.6.1.4.1.2011.6.139.11.1.27.1
		hwWlanStaBlacklistProfileTable OBJECT-TYPE
			SYNTAX SEQUENCE OF HwWlanStaBlacklistProfileEntry
			MAX-ACCESS not-accessible
			STATUS current
			DESCRIPTION
				"This table is used to create STA blacklist profiles."
			::= { hwWlanStaBlacklistConfig 1 }

		
		-- 1.3.6.1.4.1.2011.6.139.11.1.27.1.1
		hwWlanStaBlacklistProfileEntry OBJECT-TYPE
			SYNTAX HwWlanStaBlacklistProfileEntry
			MAX-ACCESS not-accessible
			STATUS current
			DESCRIPTION
				"The index of this table is hwWlanStaBlacklistProfileName."
			INDEX { hwWlanStaBlacklistProfileName }
			::= { hwWlanStaBlacklistProfileTable 1 }

		
		HwWlanStaBlacklistProfileEntry ::=
			SEQUENCE { 
				hwWlanStaBlacklistProfileName
					OCTET STRING,
				hwWlanStaBlacklistProfileRowStatus
					RowStatus
			 }

		-- 1.3.6.1.4.1.2011.6.139.11.1.27.1.1.1
		hwWlanStaBlacklistProfileName OBJECT-TYPE
			SYNTAX OCTET STRING (SIZE (1..35))
			MAX-ACCESS not-accessible
			STATUS current
			DESCRIPTION 
				"This object indicates the STA blacklist profile name. It is the index of the table."
			::= { hwWlanStaBlacklistProfileEntry 1 }

		
		-- 1.3.6.1.4.1.2011.6.139.11.1.27.1.1.2
		hwWlanStaBlacklistProfileRowStatus OBJECT-TYPE
			SYNTAX RowStatus
			MAX-ACCESS read-write
			STATUS current
			DESCRIPTION
				"This object indicates the row status of this table. ROWSTATUS_CREATEANDFLOW and ROWSTATUS_DESTROY are commonly used."
			::= { hwWlanStaBlacklistProfileEntry 2 }

		
		-- 1.3.6.1.4.1.2011.6.139.11.1.27.2
		hwWlanStaBlacklistProfileConfigTable OBJECT-TYPE
			SYNTAX SEQUENCE OF HwWlanStaBlacklistProfileConfigEntry
			MAX-ACCESS not-accessible
			STATUS current
			DESCRIPTION
				"This table is used to configure STA blacklist profiles."
			::= { hwWlanStaBlacklistConfig 2 }

		
		-- 1.3.6.1.4.1.2011.6.139.11.1.27.2.1
		hwWlanStaBlacklistProfileConfigEntry OBJECT-TYPE
			SYNTAX HwWlanStaBlacklistProfileConfigEntry
			MAX-ACCESS not-accessible
			STATUS current
			DESCRIPTION
				"The indexes of this table are hwWlanStaBlacklistProfileName and hwWlanStaBlacklistStaMac."
			INDEX { hwWlanStaBlacklistStaMac, hwWlanStaBlacklistProfileName }
			::= { hwWlanStaBlacklistProfileConfigTable 1 }

		
		HwWlanStaBlacklistProfileConfigEntry ::=
			SEQUENCE { 
				hwWlanStaBlacklistStaMac
					MacAddress,
				hwWlanStaBlacklistRowStatus
					RowStatus
			 }

		-- 1.3.6.1.4.1.2011.6.139.11.1.27.2.1.1
		hwWlanStaBlacklistStaMac OBJECT-TYPE
			SYNTAX MacAddress
			MAX-ACCESS not-accessible
			STATUS current
			DESCRIPTION
				"This object indicates the blacklist."
			::= { hwWlanStaBlacklistProfileConfigEntry 1 }

		
		-- 1.3.6.1.4.1.2011.6.139.11.1.27.2.1.2
		hwWlanStaBlacklistRowStatus OBJECT-TYPE
			SYNTAX RowStatus
			MAX-ACCESS read-write
			STATUS current
			DESCRIPTION 
				"This object indicates the row status of this table. ROWSTATUS_CREATEANDFLOW and ROWSTATUS_DESTROY are commonly used."
			::= { hwWlanStaBlacklistProfileConfigEntry 2 }

		--1.3.6.1.4.1.2011.6.139.11.1.28
		hwWidsProfileTable OBJECT-TYPE
			SYNTAX SEQUENCE OF HwWidsProfileEntry 
			MAX-ACCESS not-accessible
			STATUS current
			DESCRIPTION 
				"This table is used to configure WIDS classify profiles, WIDS attack profiles, and WIDS contain profiles."
			::= { hwWlanConfigObjects 28 }

		--1.3.6.1.4.1.2011.6.139.11.1.28.1
		hwWidsProfileEntry OBJECT-TYPE
			SYNTAX HwWidsProfileEntry 
			MAX-ACCESS not-accessible
			STATUS current
			DESCRIPTION 
				"The index of this table is hwWidsProfileName."
			INDEX { hwWidsProfileName }
			::= { hwWidsProfileTable 1 }


		HwWidsProfileEntry ::=
			SEQUENCE {				
				hwWidsProfileName
					OCTET STRING,
				hwWidsProfileRowStatus
					RowStatus,
				hwWidsDeviceReportInterval
					Unsigned32,
				hwWidsDeviceSyncInterval
					Unsigned32,
				hwWidsSpoofProfile
					OCTET STRING,
				hwWidsWhitelistProfile
					OCTET STRING,
				hwWidsBruteForceDetectInterval
					Unsigned32,
				hwWidsBruteForceDetectThreshold
					Unsigned32,
				hwWidsBruteForceQuietTime
					Unsigned32,
				hwWidsFloodDetectInterval
					Unsigned32,
				hwWidsFloodDetectThreshold
					Unsigned32,
				hwWidsFloodQuietTime
					Unsigned32,
				hwWidsWeakIvQuietTime
					Unsigned32,
				hwWidsSpoofQuietTime
					Unsigned32,
				hwWidsDynamicBlackListSwitch
					INTEGER,
				hwWidsRogueContainModeBmp
					Unsigned32
			 }

		 --1.3.6.1.4.1.2011.6.139.11.1.28.1.1
		hwWidsProfileName OBJECT-TYPE
			SYNTAX OCTET STRING (SIZE (1..35))
			MAX-ACCESS not-accessible
			STATUS current
			DESCRIPTION 
				"This object indicates the name of a WIDS profile. It is the index of the table."
			::= { hwWidsProfileEntry 1 }

		
		-- 1.3.6.1.4.1.2011.6.139.11.1.28.1.5
		hwWidsProfileRowStatus OBJECT-TYPE
			SYNTAX RowStatus
			MAX-ACCESS read-write
			STATUS current
			DESCRIPTION 
				"This object indicates the row status of this table. ROWSTATUS_CREATEANDFLOW and ROWSTATUS_DESTROY are commonly used."
			::= { hwWidsProfileEntry 5 }

		

		-- 1.3.6.1.4.1.2011.6.139.11.1.28.1.6
		hwWidsDeviceReportInterval OBJECT-TYPE
			SYNTAX Unsigned32 (10..3600)
			MAX-ACCESS read-write
			STATUS current
			DESCRIPTION 
				"This object indicates the device detection reporting interval. The default value is 300 seconds."
			::= { hwWidsProfileEntry 6 }

		 --1.3.6.1.4.1.2011.6.139.11.1.28.1.7
		hwWidsDeviceSyncInterval OBJECT-TYPE
			SYNTAX Unsigned32 (120..360)
			MAX-ACCESS read-write
			STATUS current
			DESCRIPTION 
				"This object indicates the interval for APs to report all device information to an AC. The default value is 360 minutes."
			::= { hwWidsProfileEntry 7 }

		 --1.3.6.1.4.1.2011.6.139.11.1.28.1.8
		hwWidsSpoofProfile OBJECT-TYPE
			SYNTAX OCTET STRING (SIZE (0..35))
			MAX-ACCESS read-write
			STATUS current
			DESCRIPTION 
				"This object indicates the name of a WIDS spoof profile."
			::= { hwWidsProfileEntry 8 }

		 --1.3.6.1.4.1.2011.6.139.11.1.28.1.9
		hwWidsWhitelistProfile OBJECT-TYPE
			SYNTAX OCTET STRING (SIZE (0..35))
			MAX-ACCESS read-write
			STATUS current
			DESCRIPTION 
				"This object indicates the name of a WIDS confident profile."
			::= { hwWidsProfileEntry 9 }

		

		-- 1.3.6.1.4.1.2011.6.139.11.1.28.1.10
		hwWidsBruteForceDetectInterval OBJECT-TYPE
			SYNTAX Unsigned32 (10..120)
			MAX-ACCESS read-write
			STATUS current
			DESCRIPTION 
				"This object indicates the interval for brute force attack detection. The default value is 60. It is expressed in s."
			::= { hwWidsProfileEntry 10 }

		 --1.3.6.1.4.1.2011.6.139.11.1.28.1.11
		hwWidsBruteForceDetectThreshold OBJECT-TYPE
			SYNTAX Unsigned32 (1..100)
			MAX-ACCESS read-write
			STATUS current
			DESCRIPTION 
				"This object indicates the threshold for the number of brute force attack attempts, namely, the threshold for the number of key negotiation failures within a detection period. If the number of brute-force attack attempts exceeds the threshold, the terminal initiates brute force attacks. The default value is 20."
			::= { hwWidsProfileEntry 11 }

		 --1.3.6.1.4.1.2011.6.139.11.1.28.1.12
		hwWidsBruteForceQuietTime OBJECT-TYPE
			SYNTAX Unsigned32 (60..36000)
			MAX-ACCESS read-write
			STATUS current
			DESCRIPTION 
				"This object indicates the quiet period for brute force attack alarm reporting. The default value is 600 seconds."
			::= { hwWidsProfileEntry 12 }

		

		-- 1.3.6.1.4.1.2011.6.139.11.1.28.1.13
		hwWidsFloodDetectInterval OBJECT-TYPE
			SYNTAX Unsigned32 (10..120)
			MAX-ACCESS read-write
			STATUS current
			DESCRIPTION 
				"This object indicates the flood attack detection interval. The default value is 60. It is expressed in s."
			::= { hwWidsProfileEntry 13 }

		 --1.3.6.1.4.1.2011.6.139.11.1.28.1.14
		hwWidsFloodDetectThreshold OBJECT-TYPE
			SYNTAX Unsigned32 (1..1000)
			MAX-ACCESS read-write
			STATUS current
			DESCRIPTION 
				"This object indicates the threshold for food attack detection. If the number of packets of the same type received within a detection period exceeds the threshold, flood attacks occur. The default value is 300."
			::= { hwWidsProfileEntry 14 }

		 --1.3.6.1.4.1.2011.6.139.11.1.28.1.15
		hwWidsFloodQuietTime OBJECT-TYPE
			SYNTAX Unsigned32 (60..36000)
			MAX-ACCESS read-write
			STATUS current
			DESCRIPTION 
				"This object indicates the quiet period for flood attack alarm reporting. The default value is 600 seconds."
			::= { hwWidsProfileEntry 15 }

		

		-- 1.3.6.1.4.1.2011.6.139.11.1.28.1.16
		hwWidsWeakIvQuietTime OBJECT-TYPE
			SYNTAX Unsigned32 (60..36000)
			MAX-ACCESS read-write
			STATUS current
			DESCRIPTION 
				"This object indicates the quiet period for weak IV attack alarm reporting. The default value is 600 seconds."
			::= { hwWidsProfileEntry 16 }

		
		-- 1.3.6.1.4.1.2011.6.139.11.1.28.1.17
		hwWidsSpoofQuietTime OBJECT-TYPE
			SYNTAX Unsigned32 (60..36000)
			MAX-ACCESS read-write
			STATUS current
			DESCRIPTION 
				"This object indicates the quiet period for spoofing attack alarm reporting. The default value is 600 seconds."
			::= { hwWidsProfileEntry 17 }

		 --1.3.6.1.4.1.2011.6.139.11.1.28.1.18
		hwWidsDynamicBlackListSwitch OBJECT-TYPE
			SYNTAX INTEGER
				{
				disable(1) ,
				enable(2)
				}
			MAX-ACCESS read-write
			STATUS current
			DESCRIPTION 
				"This object indicates the status of the dynamic blacklist function. The default value is 1."
			::= { hwWidsProfileEntry 18 }

		

		-- 1.3.6.1.4.1.2011.6.139.11.1.28.1.19
		hwWidsRogueContainModeBmp OBJECT-TYPE
			SYNTAX Unsigned32
			MAX-ACCESS read-write
			STATUS current
			DESCRIPTION 
				"This object indicates the bit map of rogue device countering types. The default value is 0."
			::= { hwWidsProfileEntry 19 }

		
-- 1.3.6.1.4.1.2011.6.139.11.1.32
		-- 1.3.6.1.4.1.2011.6.139.11.1.32
		hwWidsSpoofProfileTable OBJECT-TYPE
			SYNTAX SEQUENCE OF HwWidsSpoofProfileEntry 
			MAX-ACCESS not-accessible
			STATUS current
			DESCRIPTION 
				"This table is used to configure matching rules for spoof APs."
			::= { hwWlanConfigObjects 32 }

		--1.3.6.1.4.1.2011.6.139.11.1.32.1
		hwWidsSpoofProfileEntry OBJECT-TYPE
			SYNTAX HwWidsSpoofProfileEntry 
			MAX-ACCESS not-accessible
			STATUS current
			DESCRIPTION 
				"The indexes of this table are hwWidsSpoofProfileName and hwWidsSpoofSsidRegex."
			INDEX { hwWidsSpoofProfileName, hwWidsSpoofSsidRegex }
			::= { hwWidsSpoofProfileTable 1 }


		HwWidsSpoofProfileEntry ::=
			SEQUENCE {				
				hwWidsSpoofProfileName
					OCTET STRING,
				hwWidsSpoofSsidRegex
					OCTET STRING,
				hwWidsSpoofProfileRowStatus
					RowStatus 
			 }

		 --1.3.6.1.4.1.2011.6.139.11.1.32.1.1
		hwWidsSpoofProfileName OBJECT-TYPE
			SYNTAX OCTET STRING (SIZE (1..35))
			MAX-ACCESS not-accessible
			STATUS current
			DESCRIPTION 
				"This object indicates the name of a WIDS spoof profile. It is the index of the table."
			::= { hwWidsSpoofProfileEntry 1 }

		 --1.3.6.1.4.1.2011.6.139.11.1.32.1.2
		hwWidsSpoofSsidRegex OBJECT-TYPE
			SYNTAX OCTET STRING (SIZE (1..48))
			MAX-ACCESS not-accessible
			STATUS current
			DESCRIPTION 
				"This object indicates the matching rules for spoofing SSIDs."
			::= { hwWidsSpoofProfileEntry 2 }

		 --1.3.6.1.4.1.2011.6.139.11.1.32.1.3
		hwWidsSpoofProfileRowStatus OBJECT-TYPE
			SYNTAX RowStatus
			MAX-ACCESS read-write
			STATUS current
			DESCRIPTION 
				"This object indicates the row status of this table. ROWSTATUS_CREATEANDFLOW and ROWSTATUS_DESTROY are commonly used."
			::= { hwWidsSpoofProfileEntry 3 }

		--1.3.6.1.4.1.2011.6.139.11.1.33
		hwWidsWhitelistProfileMacTable OBJECT-TYPE
			SYNTAX SEQUENCE OF HwWidsWhitelistProfileMacEntry 
			MAX-ACCESS not-accessible
			STATUS current
			DESCRIPTION 
				"This table is used to configure WIDS MAC whitelists."
			::= { hwWlanConfigObjects 33 }

		--1.3.6.1.4.1.2011.6.139.11.1.33.1
		hwWidsWhitelistProfileMacEntry OBJECT-TYPE
			SYNTAX HwWidsWhitelistProfileMacEntry 
			MAX-ACCESS not-accessible
			STATUS current
			DESCRIPTION 
				"The index of this table is hwWidsWhitelistProfileName."
			INDEX { hwWidsWhitelistProfileName, hwWidsWhitelistProfileMac }
			::= { hwWidsWhitelistProfileMacTable 1 }


		HwWidsWhitelistProfileMacEntry ::=
			SEQUENCE {				
				hwWidsWhitelistProfileName
					OCTET STRING,
				hwWidsWhitelistProfileMac
					MacAddress,
				hwWidsWhitelistProfileMacRowStatus
					RowStatus 
			 }

		 --1.3.6.1.4.1.2011.6.139.11.1.33.1.1
		hwWidsWhitelistProfileName OBJECT-TYPE
			SYNTAX OCTET STRING (SIZE (1..35))
			MAX-ACCESS not-accessible
			STATUS current
			DESCRIPTION 
				"This object indicates the name of a WIDS confident profile. It is the index of the table."
			::= { hwWidsWhitelistProfileMacEntry 1 }

		 --1.3.6.1.4.1.2011.6.139.11.1.33.1.2
		hwWidsWhitelistProfileMac OBJECT-TYPE
			SYNTAX MacAddress
			MAX-ACCESS not-accessible
			STATUS current
			DESCRIPTION 
				"This object indicates the MAC address whitelist."
			::= { hwWidsWhitelistProfileMacEntry 2 }

		 --1.3.6.1.4.1.2011.6.139.11.1.33.1.3
		hwWidsWhitelistProfileMacRowStatus OBJECT-TYPE
			SYNTAX RowStatus
			MAX-ACCESS read-write
			STATUS current
			DESCRIPTION 
				"This object indicates the row status of this table. ROWSTATUS_CREATEANDFLOW and ROWSTATUS_DESTROY are commonly used."
			::= { hwWidsWhitelistProfileMacEntry 3 }

		--1.3.6.1.4.1.2011.6.139.11.1.34
		hwWidsWhitelistProfileOuiTable OBJECT-TYPE
			SYNTAX SEQUENCE OF HwWidsWhitelistProfileOuiEntry 
			MAX-ACCESS not-accessible
			STATUS current
			DESCRIPTION 
				"This table is used to configure WIDS OUI whitelists."
			::= { hwWlanConfigObjects 34 }

		--1.3.6.1.4.1.2011.6.139.11.1.34.1
		hwWidsWhitelistProfileOuiEntry OBJECT-TYPE
			SYNTAX HwWidsWhitelistProfileOuiEntry 
			MAX-ACCESS not-accessible
			STATUS current
			DESCRIPTION 
				"The index of this table is hwWidsWhitelistProfileOui."
			INDEX { hwWidsWhitelistProfileName, hwWidsWhitelistProfileOui }
			::= { hwWidsWhitelistProfileOuiTable 1 }


		HwWidsWhitelistProfileOuiEntry ::=
			SEQUENCE {				
				hwWidsWhitelistProfileOui
					OCTET STRING,
				hwWidsWhitelistProfileOuiRowStatus
					RowStatus 
			 }

		 --1.3.6.1.4.1.2011.6.139.11.1.34.1.1
		hwWidsWhitelistProfileOui OBJECT-TYPE
			SYNTAX OCTET STRING (SIZE (1..8))
			MAX-ACCESS not-accessible
			STATUS current
			DESCRIPTION 
				"This object indicates the index of the OUI whitelist in the WIDS confident profile. Its format is XX-XX-XX. XX is a hexadecimal number."
			::= { hwWidsWhitelistProfileOuiEntry 1 }

		 --1.3.6.1.4.1.2011.6.139.11.1.34.1.2
		hwWidsWhitelistProfileOuiRowStatus OBJECT-TYPE
			SYNTAX RowStatus
			MAX-ACCESS read-write
			STATUS current
			DESCRIPTION 
				"This object indicates the row status of this table. ROWSTATUS_CREATEANDFLOW and ROWSTATUS_DESTROY are commonly used."
			::= { hwWidsWhitelistProfileOuiEntry 2 }

		--1.3.6.1.4.1.2011.6.139.11.1.35
		hwWidsWhitelistProfileSsidTable OBJECT-TYPE
			SYNTAX SEQUENCE OF HwWidsWhitelistProfileSsidEntry 
			MAX-ACCESS not-accessible
			STATUS current
			DESCRIPTION 
				"This table is used to configure WIDS SSID whitelists."
			::= { hwWlanConfigObjects 35 }

		--1.3.6.1.4.1.2011.6.139.11.1.35.1
		hwWidsWhitelistProfileSsidEntry OBJECT-TYPE
			SYNTAX HwWidsWhitelistProfileSsidEntry 
			MAX-ACCESS not-accessible
			STATUS current
			DESCRIPTION 
				"The index of this table is hwWidsWhitelistProfileSsid."
			INDEX { hwWidsWhitelistProfileName, hwWidsWhitelistProfileSsid }
			::= { hwWidsWhitelistProfileSsidTable 1 }


		HwWidsWhitelistProfileSsidEntry ::=
			SEQUENCE {				
				hwWidsWhitelistProfileSsid
					OCTET STRING,
				hwWidsWhitelistProfileSsidRowStatus
					RowStatus 
			 }

		 --1.3.6.1.4.1.2011.6.139.11.1.35.1.1
		hwWidsWhitelistProfileSsid OBJECT-TYPE
			SYNTAX OCTET STRING (SIZE (1..32))
			MAX-ACCESS not-accessible
			STATUS current
			DESCRIPTION
				"This object indicates the trusted SSIDs that are case-sensitive."
			::= { hwWidsWhitelistProfileSsidEntry 1 }

		
-- 1.3.6.1.4.1.2011.6.139.11.1.35.1.2
		-- 1.3.6.1.4.1.2011.6.139.11.1.35.1.2
		hwWidsWhitelistProfileSsidRowStatus OBJECT-TYPE
			SYNTAX RowStatus
			MAX-ACCESS read-write
			STATUS current
			DESCRIPTION
				"This object indicates the row status of this table. ROWSTATUS_CREATEANDFLOW and ROWSTATUS_DESTROY are commonly used."
			::= { hwWidsWhitelistProfileSsidEntry 2 }

		
-- 1.3.6.1.4.1.2011.6.139.11.1.36
		-- 1.3.6.1.4.1.2011.6.139.11.1.36
		hwWlanMeshProfileTable OBJECT-TYPE
			SYNTAX SEQUENCE OF HwWlanMeshProfileEntry
			MAX-ACCESS not-accessible
			STATUS current
			DESCRIPTION
				"This table is used to configure and query Mesh profile parameters."
			::= { hwWlanConfigObjects 36 }

		
-- 1.3.6.1.4.1.2011.6.139.11.1.36.1
		-- 1.3.6.1.4.1.2011.6.139.11.1.36.1
		hwWlanMeshProfileEntry OBJECT-TYPE
			SYNTAX HwWlanMeshProfileEntry
			MAX-ACCESS not-accessible
			STATUS current
			DESCRIPTION
				"The index of this table is hwWlanMeshProfileName."
			INDEX { hwWlanMeshProfileName }
			::= { hwWlanMeshProfileTable 1 }

		
		HwWlanMeshProfileEntry ::=
			SEQUENCE { 
				hwWlanMeshProfileName
					OCTET STRING,
				hwWlanMeshID
					OCTET STRING,
				hwWlanMeshDhcpTrustPort
					INTEGER,
				hwWlanMeshLinkReportInterval
					Unsigned32,
				hwWlanMeshMaxLinkNum
					Unsigned32,
				hwWlanMeshRssiThreshold
					Integer32,
				hwWlanMeshSecurityProfileName
					OCTET STRING,
				hwWlanMeshProfileHandoverProfileName
					OCTET STRING,
				hwWlanMeshFwaSwitch
					INTEGER,
				hwWlanMeshFwaEdcaMode
					INTEGER,
				hwWlanMeshProfileRowStatus
					RowStatus,
				hwWlanMeshClientEdcaVoiceECWmax
					Unsigned32,
				hwWlanMeshClientEdcaVoiceECWmin
					Unsigned32,
				hwWlanMeshClientEdcaVoiceAIFSN 
					Unsigned32,
				hwWlanMeshClientEdcaVoiceTXOPLimit
					Unsigned32,
				hwWlanMeshClientEdcaVideoECWmax 
					Unsigned32,
				hwWlanMeshClientEdcaVideoECWmin 
					Unsigned32,
				hwWlanMeshClientEdcaVideoAIFSN
					Unsigned32,
				hwWlanMeshClientEdcaVideoTXOPLimit
					Unsigned32,
				hwWlanMeshClientEdcaBeECWmax
					Unsigned32,
				hwWlanMeshClientEdcaBeECWmin
					Unsigned32,
				hwWlanMeshClientEdcaBeAIFSN
					Unsigned32,
				hwWlanMeshClientEdcaBeTXOPLimit
					Unsigned32,
				hwWlanMeshClientEdcaBkECWmax
					Unsigned32,
				hwWlanMeshClientEdcaBkECWmin
					Unsigned32,
				hwWlanMeshClientEdcaBkAIFSN
					Unsigned32,
				hwWlanMeshClientEdcaBkTXOPLimit
					Unsigned32,
				hwWlanMeshNdTrustPort
					INTEGER,
				hwWlanMeshLinkAgingTime
					Unsigned32,
				hwWlanMeshProfilePriorityMapTrustMode
					INTEGER,
				hwWlanMeshProfilePriorityDscpMap80211e
					OCTET STRING
			 }

-- 1.3.6.1.4.1.2011.6.139.11.1.36.1.1
		-- 1.3.6.1.4.1.2011.6.139.11.1.36.1.1
		hwWlanMeshProfileName OBJECT-TYPE
			SYNTAX OCTET STRING (SIZE (1..35))
			MAX-ACCESS not-accessible
			STATUS current
			DESCRIPTION
				"This object indicates the name of a mesh profile. It is the index of the table."
			::= { hwWlanMeshProfileEntry 1 }

		
-- 1.3.6.1.4.1.2011.6.139.11.1.36.1.2
		-- 1.3.6.1.4.1.2011.6.139.11.1.36.1.2
		hwWlanMeshID OBJECT-TYPE
			SYNTAX OCTET STRING (SIZE (1..32))
			MAX-ACCESS read-write
			STATUS current
			DESCRIPTION
				"This object indicates the mesh ID. The value is a string of case-sensitive characters without question marks (and spaces. It cannot begin or end with double quotation marks. The default value is huaweimesh."
			::= { hwWlanMeshProfileEntry 2 }

		
-- 1.3.6.1.4.1.2011.6.139.11.1.36.1.3
		-- 1.3.6.1.4.1.2011.6.139.11.1.36.1.3
		hwWlanMeshDhcpTrustPort OBJECT-TYPE
			SYNTAX INTEGER
				{
				disable(1),
				enable(2)
				}
			MAX-ACCESS read-write
			STATUS current
			DESCRIPTION
				"This object indicates whether to enable the DHCP trusted port on an AP. The default value is 2."
			::= { hwWlanMeshProfileEntry 3 }

		
-- 1.3.6.1.4.1.2011.6.139.11.1.36.1.4
		-- 1.3.6.1.4.1.2011.6.139.11.1.36.1.4
		hwWlanMeshLinkReportInterval OBJECT-TYPE
			SYNTAX Unsigned32 (5..3600)
			MAX-ACCESS read-write
			STATUS current
			DESCRIPTION
				"This object indicates the interval for reporting mesh link information. The default value is 30 seconds."
			::= { hwWlanMeshProfileEntry 4 }

		
-- 1.3.6.1.4.1.2011.6.139.11.1.36.1.5
		-- 1.3.6.1.4.1.2011.6.139.11.1.36.1.5
		hwWlanMeshMaxLinkNum OBJECT-TYPE
			SYNTAX Unsigned32 (1..32)
			MAX-ACCESS read-write
			STATUS current
			DESCRIPTION
				"In FWA mode, the maximum number of Mesh links supported is 32,otherwise, it is 8"
			::= { hwWlanMeshProfileEntry 5 }

		
-- 1.3.6.1.4.1.2011.6.139.11.1.36.1.6
		-- 1.3.6.1.4.1.2011.6.139.11.1.36.1.6
		hwWlanMeshRssiThreshold OBJECT-TYPE
			SYNTAX Integer32 (-90..-20)
			MAX-ACCESS read-write
			STATUS current
			DESCRIPTION
				"This object indicates the valid RSSI threshold for a Mesh link route. The default value is -75 dBm."
			::= { hwWlanMeshProfileEntry 6 }

		
		-- 1.3.6.1.4.1.2011.6.139.11.1.36.1.8
		hwWlanMeshSecurityProfileName OBJECT-TYPE
			SYNTAX OCTET STRING (SIZE (1..35))
			MAX-ACCESS read-write
			STATUS current
			DESCRIPTION
				"The object indicates the bound security profile."
			::= { hwWlanMeshProfileEntry 8 }

		
-- 1.3.6.1.4.1.2011.6.139.11.1.36.1.9
		-- 1.3.6.1.4.1.2011.6.139.11.1.36.1.9
		hwWlanMeshProfileHandoverProfileName OBJECT-TYPE
			SYNTAX OCTET STRING (SIZE (0..35))
			MAX-ACCESS read-write
			STATUS current
			DESCRIPTION
				"The object indicates the bound handover profile."
			::= { hwWlanMeshProfileEntry 9 }

		
-- 1.3.6.1.4.1.2011.6.139.11.1.36.1.10
		-- 1.3.6.1.4.1.2011.6.139.11.1.36.1.10
		hwWlanMeshFwaSwitch OBJECT-TYPE
			SYNTAX INTEGER
				{
				disable(1),
				enable(2)
				}
			MAX-ACCESS read-write
			STATUS current
			DESCRIPTION
				"This object indicates the status of the FWA mode function. The default value is 1."
			::= { hwWlanMeshProfileEntry 10 }

		
-- 1.3.6.1.4.1.2011.6.139.11.1.36.1.11
		-- 1.3.6.1.4.1.2011.6.139.11.1.36.1.11
		hwWlanMeshFwaEdcaMode OBJECT-TYPE
			SYNTAX INTEGER
				{
				auto(1),
				manual(2)
				}
			MAX-ACCESS read-write
			STATUS current
			DESCRIPTION
				"This object indicates the EDCA mode in FWA mode. The default value is 1."
			::= { hwWlanMeshProfileEntry 11 }

		
-- 1.3.6.1.4.1.2011.6.139.11.1.36.1.12
		-- 1.3.6.1.4.1.2011.6.139.11.1.36.1.12
		hwWlanMeshProfileRowStatus OBJECT-TYPE
			SYNTAX RowStatus
			MAX-ACCESS read-write
			STATUS current
			DESCRIPTION
				"This object indicates the row status of this table. ROWSTATUS_CREATEANDFLOW and ROWSTATUS_DESTROY are commonly used."
			::= { hwWlanMeshProfileEntry 12 }

		
		-- 1.3.6.1.4.1.2011.6.139.11.1.36.1.13
		hwWlanMeshClientEdcaVoiceECWmax OBJECT-TYPE
			SYNTAX Unsigned32 (0..15)
			MAX-ACCESS read-write
			STATUS current
			DESCRIPTION
				"This object indicates the exponent form of the maximum contention window (ECWmax) for AC_VO packets. ECWmin and ECWmax determine the average backoff time."
			::= { hwWlanMeshProfileEntry 13 }

		
		-- 1.3.6.1.4.1.2011.6.139.11.1.36.1.14
		hwWlanMeshClientEdcaVoiceECWmin OBJECT-TYPE
			SYNTAX Unsigned32 (0..15)
			MAX-ACCESS read-write
			STATUS current
			DESCRIPTION
				"This object indicates the exponent form of the minimum contention window (ECWmin) for AC_VO packets. ECWmin and ECWmax determine the average backoff time."
			::= { hwWlanMeshProfileEntry 14 }

		
		-- 1.3.6.1.4.1.2011.6.139.11.1.36.1.15
		hwWlanMeshClientEdcaVoiceAIFSN  OBJECT-TYPE
			SYNTAX Unsigned32 (1..15)
			MAX-ACCESS read-write
			STATUS current
			DESCRIPTION
				"This object indicates the AIFSN for AC_VO packets,  which determines the channel idle time."
			::= { hwWlanMeshProfileEntry 15 }

		
		-- 1.3.6.1.4.1.2011.6.139.11.1.36.1.16
		hwWlanMeshClientEdcaVoiceTXOPLimit OBJECT-TYPE
			SYNTAX Unsigned32 (0..255)
			MAX-ACCESS read-write
			STATUS current
			DESCRIPTION
				"This object indicates the transmission opportunity limit (TXOPLimit) for AC_VO packets, which determines the maximum duration in which an STA can occupy a channel. A larger TXOPLimit value indicates a longer duration to occupy a channel."
			::= { hwWlanMeshProfileEntry 16 }

		
		-- 1.3.6.1.4.1.2011.6.139.11.1.36.1.17
		hwWlanMeshClientEdcaVideoECWmax  OBJECT-TYPE
			SYNTAX Unsigned32 (0..15)
			MAX-ACCESS read-write
			STATUS current
			DESCRIPTION
				"This object indicates the exponent form of the maximum contention window (ECWmax) for AC_VI packets. ECWmin and ECWmax determine the average backoff time."
			::= { hwWlanMeshProfileEntry 17 }

		
		-- 1.3.6.1.4.1.2011.6.139.11.1.36.1.18
		hwWlanMeshClientEdcaVideoECWmin  OBJECT-TYPE
			SYNTAX Unsigned32 (0..15)
			MAX-ACCESS read-write
			STATUS current
			DESCRIPTION
				"This object indicates the exponent form of the minimum contention window (ECWmin) for AC_VI packets. ECWmin and ECWmax determine the average backoff time."
			::= { hwWlanMeshProfileEntry 18 }

		
		-- 1.3.6.1.4.1.2011.6.139.11.1.36.1.19
		hwWlanMeshClientEdcaVideoAIFSN OBJECT-TYPE
			SYNTAX Unsigned32 (1..15)
			MAX-ACCESS read-write
			STATUS current
			DESCRIPTION
				"This object indicates the AIFSN for AC_VI packets,  which determines the channel idle time."
			::= { hwWlanMeshProfileEntry 19 }

		
		-- 1.3.6.1.4.1.2011.6.139.11.1.36.1.20
		hwWlanMeshClientEdcaVideoTXOPLimit OBJECT-TYPE
			SYNTAX Unsigned32 (0..255)
			MAX-ACCESS read-write
			STATUS current
			DESCRIPTION
				"This object indicates the transmission opportunity limit (TXOPLimit) for AC_VI packets, which determines the maximum duration in which an STA can occupy a channel. A larger TXOPLimit value indicates a longer duration to occupy a channel."
			::= { hwWlanMeshProfileEntry 20 }

		
		-- 1.3.6.1.4.1.2011.6.139.11.1.36.1.21
		hwWlanMeshClientEdcaBeECWmax OBJECT-TYPE
			SYNTAX Unsigned32 (0..15)
			MAX-ACCESS read-write
			STATUS current
			DESCRIPTION
				"This object indicates the exponent form of the maximum contention window (ECWmax) for AC_BE packets. ECWmin and ECWmax determine the average backoff time."
			::= { hwWlanMeshProfileEntry 21 }

		
		-- 1.3.6.1.4.1.2011.6.139.11.1.36.1.22
		hwWlanMeshClientEdcaBeECWmin OBJECT-TYPE
			SYNTAX Unsigned32 (0..15)
			MAX-ACCESS read-write
			STATUS current
			DESCRIPTION
				"This object indicates the exponent form of the minimum contention window (ECWmin) for AC_BE packets. ECWmin and ECWmax determine the average backoff time."
			::= { hwWlanMeshProfileEntry 22 }

		
		-- 1.3.6.1.4.1.2011.6.139.11.1.36.1.23
		hwWlanMeshClientEdcaBeAIFSN OBJECT-TYPE
			SYNTAX Unsigned32 (1..15)
			MAX-ACCESS read-write
			STATUS current
			DESCRIPTION
				"This object indicates the AIFSN for AC_BE packets,  which determines the channel idle time."
			::= { hwWlanMeshProfileEntry 23 }

		
		-- 1.3.6.1.4.1.2011.6.139.11.1.36.1.24
		hwWlanMeshClientEdcaBeTXOPLimit OBJECT-TYPE
			SYNTAX Unsigned32 (0..255)
			MAX-ACCESS read-write
			STATUS current
			DESCRIPTION
				"This object indicates the transmission opportunity limit (TXOPLimit) for AC_BE packets, which determines the maximum duration in which an STA can occupy a channel. A larger TXOPLimit value indicates a longer duration to occupy a channel."
			::= { hwWlanMeshProfileEntry 24 }

		
		-- 1.3.6.1.4.1.2011.6.139.11.1.36.1.25
		hwWlanMeshClientEdcaBkECWmax OBJECT-TYPE
			SYNTAX Unsigned32 (0..15)
			MAX-ACCESS read-write
			STATUS current
			DESCRIPTION
				"This object indicates the exponent form of the maximum contention window (ECWmax) for AC_BK packets. ECWmin and ECWmax determine the average backoff time."
			::= { hwWlanMeshProfileEntry 25 }

		
		-- 1.3.6.1.4.1.2011.6.139.11.1.36.1.26
		hwWlanMeshClientEdcaBkECWmin OBJECT-TYPE
			SYNTAX Unsigned32 (0..15)
			MAX-ACCESS read-write
			STATUS current
			DESCRIPTION
				"This object indicates the exponent form of the minimum contention window (ECWmin) for AC_BK packets. ECWmin and ECWmax determine the average backoff time."
			::= { hwWlanMeshProfileEntry 26 }

		
		-- 1.3.6.1.4.1.2011.6.139.11.1.36.1.27
		hwWlanMeshClientEdcaBkAIFSN OBJECT-TYPE
			SYNTAX Unsigned32 (1..15)
			MAX-ACCESS read-write
			STATUS current
			DESCRIPTION
				"This object indicates the AIFSN for AC_BK packets,  which determines the channel idle time."
			::= { hwWlanMeshProfileEntry 27 }

		
		-- 1.3.6.1.4.1.2011.6.139.11.1.36.1.28
		hwWlanMeshClientEdcaBkTXOPLimit OBJECT-TYPE
			SYNTAX Unsigned32 (0..255)
			MAX-ACCESS read-write
			STATUS current
			DESCRIPTION
				"This object indicates the transmission opportunity limit (TXOPLimit) for AC_BK packets, which determines the maximum duration in which an STA can occupy a channel. A larger TXOPLimit value indicates a longer duration to occupy a channel."
			::= { hwWlanMeshProfileEntry 28 }

		
		-- 1.3.6.1.4.1.2011.6.139.11.1.36.1.29
		hwWlanMeshNdTrustPort OBJECT-TYPE
			SYNTAX INTEGER
				{
				disable(1),
				enable(2)
				}
			MAX-ACCESS read-write
			STATUS current
			DESCRIPTION
				"This object indicates whether to enable the ND trusted port on an AP. The default value is 2."
			::= { hwWlanMeshProfileEntry 29 }
			
			
		-- 1.3.6.1.4.1.2011.6.139.11.1.36.1.30
		hwWlanMeshLinkAgingTime OBJECT-TYPE
			SYNTAX Unsigned32 (5..60)
			MAX-ACCESS read-write
			STATUS current
			DESCRIPTION
				"This object indicates the mesh aging time."
			::= { hwWlanMeshProfileEntry 30 }
			
		-- 1.3.6.1.4.1.2011.6.139.11.1.36.1.31
		hwWlanMeshProfilePriorityMapTrustMode OBJECT-TYPE
			SYNTAX INTEGER
				{
				trustDSCP(1),
				trust8021P(2)
				}
			MAX-ACCESS read-write
			STATUS current
			DESCRIPTION
				"Description."
			::= { hwWlanMeshProfileEntry 31 }

		
		-- 1.3.6.1.4.1.2011.6.139.11.1.36.1.32
		hwWlanMeshProfilePriorityDscpMap80211e OBJECT-TYPE
			SYNTAX OCTET STRING (SIZE (1..256))
			MAX-ACCESS read-write
			STATUS current
			DESCRIPTION
				"Description."
			::= { hwWlanMeshProfileEntry 32 }

-- 1.3.6.1.4.1.2011.6.139.11.1.37
		hwWlanMeshWhitelistProfileTable OBJECT-TYPE
			SYNTAX SEQUENCE OF HwWlanMeshWhitelistProfileEntry
			MAX-ACCESS not-accessible
			STATUS current
			DESCRIPTION
				"This table describes the Mesh whitelist profile."
			::= { hwWlanConfigObjects 37 }

		
-- 1.3.6.1.4.1.2011.6.139.11.1.37.1
		-- 1.3.6.1.4.1.2011.6.139.11.1.37.1
		hwWlanMeshWhitelistProfileEntry OBJECT-TYPE
			SYNTAX HwWlanMeshWhitelistProfileEntry
			MAX-ACCESS not-accessible
			STATUS current
			DESCRIPTION
				"The index of this table is hwWlanMeshWhitelistProfileName."
			INDEX { hwWlanMeshWhitelistProfileName }
			::= { hwWlanMeshWhitelistProfileTable 1 }

		
		HwWlanMeshWhitelistProfileEntry ::=
			SEQUENCE { 
				hwWlanMeshWhitelistProfileName
					OCTET STRING,
				hwWlanMeshWhitelistProfileRowStatus
					RowStatus
			 }

-- 1.3.6.1.4.1.2011.6.139.11.1.37.1.1
		-- 1.3.6.1.4.1.2011.6.139.11.1.37.1.1
		hwWlanMeshWhitelistProfileName OBJECT-TYPE
			SYNTAX OCTET STRING (SIZE (1..35))
			MAX-ACCESS not-accessible
			STATUS current
			DESCRIPTION
				"This object indicates the name of a mesh profile."
			::= { hwWlanMeshWhitelistProfileEntry 1 }

		
-- 1.3.6.1.4.1.2011.6.139.11.1.37.1.2
		-- 1.3.6.1.4.1.2011.6.139.11.1.37.1.2
		hwWlanMeshWhitelistProfileRowStatus OBJECT-TYPE
			SYNTAX RowStatus
			MAX-ACCESS read-write
			STATUS current
			DESCRIPTION
				"This object indicates the row status of this table. ROWSTATUS_CREATEANDFLOW and ROWSTATUS_DESTROY are commonly used."
			::= { hwWlanMeshWhitelistProfileEntry 2 }

		
-- 1.3.6.1.4.1.2011.6.139.11.1.38
		-- 1.3.6.1.4.1.2011.6.139.11.1.38
		hwWlanMeshWhitelistProfileConfigTable OBJECT-TYPE
			SYNTAX SEQUENCE OF HwWlanMeshWhitelistProfileConfigEntry
			MAX-ACCESS not-accessible
			STATUS current
			DESCRIPTION
				"This table describes Mesh whitelists in the Mesh whitelist profile."
			::= { hwWlanConfigObjects 38 }

		
-- 1.3.6.1.4.1.2011.6.139.11.1.38.1
		-- 1.3.6.1.4.1.2011.6.139.11.1.38.1
		hwWlanMeshWhitelistProfileConfigEntry OBJECT-TYPE
			SYNTAX HwWlanMeshWhitelistProfileConfigEntry
			MAX-ACCESS not-accessible
			STATUS current
			DESCRIPTION
				"Indexes of this table are hwWlanMeshWhitelistProfileName and hwWlanMeshWhitelistPeerApMac."
			INDEX { hwWlanMeshWhitelistProfileName,hwWlanMeshWhitelistPeerApMac }
			::= { hwWlanMeshWhitelistProfileConfigTable 1 }


		HwWlanMeshWhitelistProfileConfigEntry ::=
			SEQUENCE {				
				hwWlanMeshWhitelistPeerApMac
					MacAddress,
				hwWlanMeshWhitelistRowStatus
					RowStatus
			 }

		 --1.3.6.1.4.1.2011.6.139.11.1.38.1.1
		hwWlanMeshWhitelistPeerApMac OBJECT-TYPE
			SYNTAX MacAddress
			MAX-ACCESS not-accessible
			STATUS current
			DESCRIPTION 
				"This object indicates the whitelist."
			::= { hwWlanMeshWhitelistProfileConfigEntry 1 }

		 --1.3.6.1.4.1.2011.6.139.11.1.38.1.2
		hwWlanMeshWhitelistRowStatus OBJECT-TYPE
			SYNTAX RowStatus
			MAX-ACCESS read-write
			STATUS current
			DESCRIPTION 
				"This object indicates the row status of this table. ROWSTATUS_CREATEANDFLOW and ROWSTATUS_DESTROY are commonly used."
			::= { hwWlanMeshWhitelistProfileConfigEntry 2 }

		--1.3.6.1.4.1.2011.6.139.11.1.39
		hwWlanMeshHandoverProfileTable OBJECT-TYPE
			SYNTAX SEQUENCE OF HwWlanMeshHandoverProfileEntry 
			MAX-ACCESS not-accessible
			STATUS current
			DESCRIPTION 
				"This table is used to configure and query Mesh handover profile parameters."
			::= { hwWlanConfigObjects 39 }

		--1.3.6.1.4.1.2011.6.139.11.1.39.1
		hwWlanMeshHandoverProfileEntry OBJECT-TYPE
			SYNTAX HwWlanMeshHandoverProfileEntry 
			MAX-ACCESS not-accessible
			STATUS current
			DESCRIPTION 
				"The index of this table is hwWlanMeshHandoverProfileName."
			INDEX { hwWlanMeshHandoverProfileName }
			::= { hwWlanMeshHandoverProfileTable 1 }


		HwWlanMeshHandoverProfileEntry ::=
			SEQUENCE {				
				hwWlanMeshHandoverProfileName
					OCTET STRING,
				hwWlanMeshHOLinkProbeInterval
					Unsigned32,
				hwWlanMeshHOMinRssiThreshold
					Integer32,
				hwWlanMeshHOMaxRssiThreshold
					Integer32,
				hwWlanMeshHOLinkHoldPeriod
					Unsigned32,
				hwWlanMeshHORssiMargin
					Unsigned32,
				hwWlanMeshHOLocationBasedAlgorithmEnable
					INTEGER,
				hwWlanMeshHOMovingDirection
					INTEGER,
				hwWlanMeshHOPNCriteriaObserveTime
					Unsigned32,
				hwWlanMeshHOPNCriteriaQualifyTime
					Unsigned32,
				hwWlanMeshUrgentHandoverLowRateThreshold
					Unsigned32,
				hwWlanMeshUrgentHandoverLowRatePeriod
					Unsigned32,
				hwWlanMeshUrgentHandoverPunishmentPeriod
					Unsigned32,
				hwWlanMeshUrgentHandoverPunishmentRssi
					Unsigned32,
				hwWlanMeshHandoverProfileRowStatus
					RowStatus 
			 }

		 --1.3.6.1.4.1.2011.6.139.11.1.39.1.1
		hwWlanMeshHandoverProfileName OBJECT-TYPE
			SYNTAX OCTET STRING (SIZE (1..35))
			MAX-ACCESS not-accessible
			STATUS current
			DESCRIPTION 
				"This object indicates the name of a mesh profile. It is the index of the table."
			::= { hwWlanMeshHandoverProfileEntry 1 }

		 --1.3.6.1.4.1.2011.6.139.11.1.39.1.2
		hwWlanMeshHOLinkProbeInterval OBJECT-TYPE
			SYNTAX Unsigned32 (50..6000)
			MAX-ACCESS read-write
			STATUS current
			DESCRIPTION 
				"Description."
			::= { hwWlanMeshHandoverProfileEntry 2 }

		 --1.3.6.1.4.1.2011.6.139.11.1.39.1.3
		hwWlanMeshHOMinRssiThreshold OBJECT-TYPE
			SYNTAX Integer32 (-90..-20)
			MAX-ACCESS read-write
			STATUS current
			DESCRIPTION 
				"Description."
			::= { hwWlanMeshHandoverProfileEntry 3 }

		 --1.3.6.1.4.1.2011.6.139.11.1.39.1.4
		hwWlanMeshHOMaxRssiThreshold OBJECT-TYPE
			SYNTAX Integer32 (-90..0)
			MAX-ACCESS read-write
			STATUS current
			DESCRIPTION 
				"Description."
			::= { hwWlanMeshHandoverProfileEntry 4 }

		 --1.3.6.1.4.1.2011.6.139.11.1.39.1.5
		hwWlanMeshHOLinkHoldPeriod OBJECT-TYPE
			SYNTAX Unsigned32 (1000..60000)
			MAX-ACCESS read-write
			STATUS current
			DESCRIPTION 
				"Description."
			::= { hwWlanMeshHandoverProfileEntry 5 }

		 --1.3.6.1.4.1.2011.6.139.11.1.39.1.6
		hwWlanMeshHORssiMargin OBJECT-TYPE
			SYNTAX Unsigned32 (1..70)
			MAX-ACCESS read-write
			STATUS current
			DESCRIPTION 
				"Description."
			::= { hwWlanMeshHandoverProfileEntry 6 }

		 --1.3.6.1.4.1.2011.6.139.11.1.39.1.7
		hwWlanMeshHOLocationBasedAlgorithmEnable OBJECT-TYPE
			SYNTAX INTEGER
				{
				disable(1) ,
				enable(2)
				}
			MAX-ACCESS read-write
			STATUS current
			DESCRIPTION 
				"Description."
			::= { hwWlanMeshHandoverProfileEntry 7 }

		 --1.3.6.1.4.1.2011.6.139.11.1.39.1.8
		hwWlanMeshHOMovingDirection OBJECT-TYPE
			SYNTAX INTEGER
				{
				forward(1),
				backward(2),
				undetermined(3)
				}
			MAX-ACCESS read-write
			STATUS current
			DESCRIPTION 
				"Description."
			::= { hwWlanMeshHandoverProfileEntry 8 }

		 --1.3.6.1.4.1.2011.6.139.11.1.39.1.9
		hwWlanMeshHOPNCriteriaObserveTime OBJECT-TYPE
			SYNTAX Unsigned32 (1..10)
			MAX-ACCESS read-write
			STATUS current
			DESCRIPTION 
				"Description."
			::= { hwWlanMeshHandoverProfileEntry 9 }

		 --1.3.6.1.4.1.2011.6.139.11.1.39.1.10
		hwWlanMeshHOPNCriteriaQualifyTime OBJECT-TYPE
			SYNTAX Unsigned32 (1..10)
			MAX-ACCESS read-write
			STATUS current
			DESCRIPTION 
				"Description."
			::= { hwWlanMeshHandoverProfileEntry 10 }

		 --1.3.6.1.4.1.2011.6.139.11.1.39.1.11
		hwWlanMeshUrgentHandoverLowRateThreshold OBJECT-TYPE
			SYNTAX Unsigned32 (1..1300)
			MAX-ACCESS read-write
			STATUS current
			DESCRIPTION 
				"Description."
			::= { hwWlanMeshHandoverProfileEntry 11 }

		 --1.3.6.1.4.1.2011.6.139.11.1.39.1.12
		hwWlanMeshUrgentHandoverLowRatePeriod OBJECT-TYPE
			SYNTAX Unsigned32 (0..10000)
			MAX-ACCESS read-write
			STATUS current
			DESCRIPTION 
				"Description."
			::= { hwWlanMeshHandoverProfileEntry 12 }

		 --1.3.6.1.4.1.2011.6.139.11.1.39.1.13
		hwWlanMeshUrgentHandoverPunishmentPeriod OBJECT-TYPE
			SYNTAX Unsigned32 (0..10000)
			MAX-ACCESS read-write
			STATUS current
			DESCRIPTION 
				"Description."
			::= { hwWlanMeshHandoverProfileEntry 13 }

		 --1.3.6.1.4.1.2011.6.139.11.1.39.1.14
		hwWlanMeshUrgentHandoverPunishmentRssi OBJECT-TYPE
			SYNTAX Unsigned32 (0..50)
			MAX-ACCESS read-write
			STATUS current
			DESCRIPTION 
				"Description."
			::= { hwWlanMeshHandoverProfileEntry 14 }

		 --1.3.6.1.4.1.2011.6.139.11.1.39.1.15
		hwWlanMeshHandoverProfileRowStatus OBJECT-TYPE
			SYNTAX RowStatus
			MAX-ACCESS read-write
			STATUS current
			DESCRIPTION 
				"This object indicates the row status of this table. ROWSTATUS_CREATEANDFLOW and ROWSTATUS_DESTROY are commonly used."
			::= { hwWlanMeshHandoverProfileEntry 15 }

		--1.3.6.1.4.1.2011.6.139.11.1.40
		hwWdsProfileTable OBJECT-TYPE
			SYNTAX SEQUENCE OF HwWdsProfileEntry 
			MAX-ACCESS not-accessible
			STATUS current
			DESCRIPTION 
				"This table is used to configure and query WDS profile parameters."
			::= { hwWlanConfigObjects 40 }

		--1.3.6.1.4.1.2011.6.139.11.1.40.1
		hwWdsProfileEntry OBJECT-TYPE
			SYNTAX HwWdsProfileEntry 
			MAX-ACCESS not-accessible
			STATUS current
			DESCRIPTION 
				"The index of this table is hwWdsProfileName."
			INDEX { hwWdsProfileName }
			::= { hwWdsProfileTable 1 }


		HwWdsProfileEntry ::=
			SEQUENCE {				
				hwWdsProfileName
					OCTET STRING,
				hwWdsName
					OCTET STRING,
				hwWdsMode
					INTEGER,
				hwWdsDhcpTrustPort
					INTEGER,
				hwWdsVlanTagged
					OCTET STRING,
				hwWdsSecurityProfileName
					OCTET STRING,
				hwWdsProfileRowStatus
					RowStatus,
				hwWdsNdTrustPort
					INTEGER,
				hwWdsProfilePriorityMapTrustMode
					INTEGER,
				hwWdsProfilePriorityDscpMap80211e
					OCTET STRING
			 }

		 --1.3.6.1.4.1.2011.6.139.11.1.40.1.1
		hwWdsProfileName OBJECT-TYPE
			SYNTAX OCTET STRING (SIZE (1..35))
			MAX-ACCESS not-accessible
			STATUS current
			DESCRIPTION 
				"This object indicates the name of a WDS profile. It is the index of the table."
			::= { hwWdsProfileEntry 1 }

		
		-- 1.3.6.1.4.1.2011.6.139.11.1.40.1.2
		hwWdsName OBJECT-TYPE
			SYNTAX OCTET STRING (SIZE (1..32))
			MAX-ACCESS read-write
			STATUS current
			DESCRIPTION
				"This object indicates the WDS identifier. The value is a string of case-sensitive characters without question marks and spaces. It cannot begin or end with double quotation marks.
                                The default value is huaweiwds."
			DEFVAL { "HUAWEI-WLAN-WDS" }
			::= { hwWdsProfileEntry 2 }

		
		-- 1.3.6.1.4.1.2011.6.139.11.1.40.1.3
		hwWdsMode OBJECT-TYPE
			SYNTAX INTEGER
				{ 
				middle(1),
				root(2),
				leaf(3)
				}
			MAX-ACCESS read-write
			STATUS current
			DESCRIPTION 
				"This object indicates the mode of the WDS. The default value is 3."
			::= { hwWdsProfileEntry 3 }

		-- 1.3.6.1.4.1.2011.6.139.11.1.40.1.4
		hwWdsDhcpTrustPort OBJECT-TYPE
			SYNTAX INTEGER
				{
				disable(1) ,
				enable(2)
				}
			MAX-ACCESS read-write
			STATUS current
			DESCRIPTION 
				"This object indicates whether to enable the DHCP trusted port on an AP. The default value is 2."
			::= { hwWdsProfileEntry 4 }


		-- 1.3.6.1.4.1.2011.6.139.11.1.40.1.5
		hwWdsVlanTagged OBJECT-TYPE
			SYNTAX OCTET STRING
			MAX-ACCESS read-write
			STATUS current
			DESCRIPTION 
				"This object indicates the tagged VLAN in a bridge profile. It is used to add one or a group of VLANs to the WDS bridge profile in tagged mode. By default, no VLAN is configured in the WDS bridge profile."
			::= { hwWdsProfileEntry 5 }


		-- 1.3.6.1.4.1.2011.6.139.11.1.40.1.6
		hwWdsSecurityProfileName OBJECT-TYPE
			SYNTAX OCTET STRING (SIZE (1..35))
			MAX-ACCESS read-write
			STATUS current
			DESCRIPTION 
				"The object indicates the bound security profile."
			::= { hwWdsProfileEntry 6 }


		-- 1.3.6.1.4.1.2011.6.139.11.1.40.1.8
		hwWdsProfileRowStatus OBJECT-TYPE
			SYNTAX RowStatus
			MAX-ACCESS read-write
			STATUS current
			DESCRIPTION 
				"This object indicates the row status of this table. ROWSTATUS_CREATEANDFLOW and ROWSTATUS_DESTROY are commonly used.ROWSTATUS_UNDEFINED: undefined ROWSTATUS_ACTIVE: active ROWSTATUS_NOTINSERVICE: notInService ROWSTATUS_NOTREADY: notReady ROWSTATUS_CREATEANDFLOW: createAndGoROWSTATUS_CREATEANDWAIT: createAndWaitROWSTATUS_DESTROY: destroy"
			::= { hwWdsProfileEntry 8 }

		
		-- 1.3.6.1.4.1.2011.6.139.11.1.40.1.9
		hwWdsNdTrustPort OBJECT-TYPE
			SYNTAX INTEGER
				{
				disable(1),
				enable(2)
				}
			MAX-ACCESS read-write
			STATUS current
			DESCRIPTION
				"This object indicates whether to enable the ND trusted port on an AP. The default value is 2."
			DEFVAL { 2 }
			::= { hwWdsProfileEntry 9 }

		
		-- 1.3.6.1.4.1.2011.6.139.11.1.40.1.10
		hwWdsProfilePriorityMapTrustMode OBJECT-TYPE
			SYNTAX INTEGER
				{
				trustDSCP(1),
				trust8021P(2)
				}
			MAX-ACCESS read-write
			STATUS current
			DESCRIPTION
				"Description."
			::= { hwWdsProfileEntry 10 }

		
		-- 1.3.6.1.4.1.2011.6.139.11.1.40.1.11
		hwWdsProfilePriorityDscpMap80211e OBJECT-TYPE
			SYNTAX OCTET STRING (SIZE (1..256))
			MAX-ACCESS read-write
			STATUS current
			DESCRIPTION
				"Description."
			::= { hwWdsProfileEntry 11 }

		--1.3.6.1.4.1.2011.6.139.11.1.41
		hwWdsWhitelistProfileTable OBJECT-TYPE
			SYNTAX SEQUENCE OF HwWdsWhitelistProfileEntry 
			MAX-ACCESS not-accessible
			STATUS current
			DESCRIPTION 
				"Description."
			::= { hwWlanConfigObjects 41 }

		--1.3.6.1.4.1.2011.6.139.11.1.41.1
		hwWdsWhitelistProfileEntry OBJECT-TYPE
			SYNTAX HwWdsWhitelistProfileEntry 
			MAX-ACCESS not-accessible
			STATUS current
			DESCRIPTION 
				"Description."
			INDEX { hwWdsWhitelistProfileName }
			::= { hwWdsWhitelistProfileTable 1 }


		HwWdsWhitelistProfileEntry ::=
			SEQUENCE {				
				hwWdsWhitelistProfileName
					OCTET STRING,
				hwWdsWhitelistProfileRowStatus
					RowStatus 
			 }

		 --1.3.6.1.4.1.2011.6.139.11.1.41.1.1
		hwWdsWhitelistProfileName OBJECT-TYPE
			SYNTAX OCTET STRING (SIZE (1..35))
			MAX-ACCESS not-accessible
			STATUS current
			DESCRIPTION 
				"Description."
			::= { hwWdsWhitelistProfileEntry 1 }

		 --1.3.6.1.4.1.2011.6.139.11.1.41.1.2
		hwWdsWhitelistProfileRowStatus OBJECT-TYPE
			SYNTAX RowStatus
			MAX-ACCESS read-write
			STATUS current
			DESCRIPTION 
				"Description."
			::= { hwWdsWhitelistProfileEntry 2 }

		--1.3.6.1.4.1.2011.6.139.11.1.42
		hwWdsWhitelistTable OBJECT-TYPE
			SYNTAX SEQUENCE OF HwWdsWhitelistEntry 
			MAX-ACCESS not-accessible
			STATUS current
			DESCRIPTION 
				"Description."
			::= { hwWlanConfigObjects 42 }

		--1.3.6.1.4.1.2011.6.139.11.1.42.1
		hwWdsWhitelistEntry OBJECT-TYPE
			SYNTAX HwWdsWhitelistEntry 
			MAX-ACCESS not-accessible
			STATUS current
			DESCRIPTION 
				"Description."
			INDEX { hwWdsWhitelistProfileName, hwWdsWhitelistPeerApMac }
			::= { hwWdsWhitelistTable 1 }


		HwWdsWhitelistEntry ::=
			SEQUENCE {				
				hwWdsWhitelistPeerApMac
					MacAddress,
				hwWdsWhitelistRowStatus
					RowStatus 
			 }

		 --1.3.6.1.4.1.2011.6.139.11.1.42.1.1
		hwWdsWhitelistPeerApMac OBJECT-TYPE
			SYNTAX MacAddress
			MAX-ACCESS not-accessible
			STATUS current
			DESCRIPTION 
				"Description."
			::= { hwWdsWhitelistEntry 1 }

		 --1.3.6.1.4.1.2011.6.139.11.1.42.1.2
		hwWdsWhitelistRowStatus OBJECT-TYPE
			SYNTAX RowStatus
			MAX-ACCESS read-write
			STATUS current
			DESCRIPTION 
				"Description."
			::= { hwWdsWhitelistEntry 2 }

		--1.3.6.1.4.1.2011.6.139.11.1.43
		hwLocationProfileTable OBJECT-TYPE
			SYNTAX SEQUENCE OF HwLocationProfileEntry 
			MAX-ACCESS not-accessible
			STATUS current
			DESCRIPTION 
				"This table is used to configure terminal location and tag location."
			::= { hwWlanConfigObjects 43 }

		--1.3.6.1.4.1.2011.6.139.11.1.43.1
		hwLocationProfileEntry OBJECT-TYPE
			SYNTAX HwLocationProfileEntry 
			MAX-ACCESS not-accessible
			STATUS current
			DESCRIPTION 
				"The index of this table is hwLocationProfileName."
			INDEX { hwLocationProfileName }
			::= { hwLocationProfileTable 1 }


		HwLocationProfileEntry ::=
			SEQUENCE {				
				hwLocationProfileName
					OCTET STRING,
				hwLocationAeroscoutTagSwitch
					INTEGER,
				hwLocationAeroscoutMuSwitch
					INTEGER,
				hwLocationAeroscoutServerPort
					Unsigned32,
				hwLocationAeroscoutViaACSwitch
					INTEGER,
				hwLocationAeroscoutViaACPort
					Unsigned32,
				hwLocationAeroscoutCompoundTime
					Unsigned32,
				hwLocationEkahauTagEnable
					INTEGER,
				hwLocationEkahauServerIPAddress
					IpAddress,
				hwLocationEkahauServerIPv6Address
					OCTET STRING,
				hwLocationEkahauServerPort
					Unsigned32,
				hwLocationEkahauViaACEnable
					INTEGER,
				hwLocationEkahauViaACPort
					Unsigned32,
				hwLocationSourceIPAddress
					IpAddress,
				hwLocationSourceIPv6Address
					OCTET STRING,
				hwLocationPrivateMuEnable
					INTEGER,
				hwLocationPrivateServerIPAddress
					IpAddress,
				hwLocationPrivateServerIPv6Address
					OCTET STRING,
				hwLocationPrivateServerPort
					Unsigned32,
				hwLocationPrivateViaACEnable
					INTEGER,
				hwLocationPrivateViaACPort
					Unsigned32,
				hwLocationPrivateReportFrequency
					Unsigned32,
				hwLocationProfileRowStatus
					RowStatus 
			 }

		 --1.3.6.1.4.1.2011.6.139.11.1.43.1.1
		hwLocationProfileName OBJECT-TYPE
			SYNTAX OCTET STRING (SIZE (1..35))
			MAX-ACCESS not-accessible
			STATUS current
			DESCRIPTION 
				"This object indicates the name of a location profile. It is the index of the table."
			::= { hwLocationProfileEntry 1 }

		 --1.3.6.1.4.1.2011.6.139.11.1.43.1.2
		hwLocationAeroscoutTagSwitch OBJECT-TYPE
			SYNTAX INTEGER
				{
				disable(1) ,
				enable(2)
				}
			MAX-ACCESS read-write
			STATUS current
			DESCRIPTION 
				"This object indicates the status of the AeroScout tag location function. The default value is 1."
			::= { hwLocationProfileEntry 2 }

		 --1.3.6.1.4.1.2011.6.139.11.1.43.1.3
		hwLocationAeroscoutMuSwitch OBJECT-TYPE
			SYNTAX INTEGER
				{
				disable(1) ,
				enable(2)
				}
			MAX-ACCESS read-write
			STATUS current
			DESCRIPTION 
				"This object indicates the status of the AeroScout MU location function. The default value is 1."
			::= { hwLocationProfileEntry 3 }

		 --1.3.6.1.4.1.2011.6.139.11.1.43.1.4
		hwLocationAeroscoutServerPort OBJECT-TYPE
			SYNTAX Unsigned32 (0|1024..65535)
			MAX-ACCESS read-write
			STATUS current
			DESCRIPTION 
				"This object indicates the port used by APs or ACs to report AeroScout location data to the AE server."
			::= { hwLocationProfileEntry 4 }

		 --1.3.6.1.4.1.2011.6.139.11.1.43.1.5
		hwLocationAeroscoutViaACSwitch OBJECT-TYPE
			SYNTAX INTEGER
				{
				disable(1) ,
				enable(2)
				}
			MAX-ACCESS read-write
			STATUS current
			DESCRIPTION 
				"This object indicates whether AeroScout tag location data is reported to the AC. This parameter has no default value."
			::= { hwLocationProfileEntry 5 }

		 --1.3.6.1.4.1.2011.6.139.11.1.43.1.6
		hwLocationAeroscoutViaACPort OBJECT-TYPE
			SYNTAX Unsigned32
			MAX-ACCESS read-write
			STATUS current
			DESCRIPTION 
				"This object indicates that AeroScout location data is reported to the AC that forwards the data to the AE. A port is configured for the AP to report location data to the AC."
			::= { hwLocationProfileEntry 6 }

		 --1.3.6.1.4.1.2011.6.139.11.1.43.1.7
		hwLocationAeroscoutCompoundTime OBJECT-TYPE
			SYNTAX Unsigned32 (0..65535)
			MAX-ACCESS read-write
			STATUS current
			DESCRIPTION 
				"This object indicates the AerosScout location data compound time. The value 0 indicates that data is not compounded and the AP reports location data in real time. The default value is 65535 and the unit is 0.1s."
			::= { hwLocationProfileEntry 7 }

		 --1.3.6.1.4.1.2011.6.139.11.1.43.1.8
		hwLocationEkahauTagEnable OBJECT-TYPE
			SYNTAX INTEGER
				{
				disable(1) ,
				enable(2)
				}
			MAX-ACCESS read-write
			STATUS current
			DESCRIPTION 
				"This object indicates the status of the Ekahau tag location function. The default value is 1."
			::= { hwLocationProfileEntry 8 }

		 --1.3.6.1.4.1.2011.6.139.11.1.43.1.9
		hwLocationEkahauServerIPAddress OBJECT-TYPE
			SYNTAX IpAddress
			MAX-ACCESS read-write
			STATUS current
			DESCRIPTION 
				"This object indicates the IP address of the location server for Ekahau tag location."
			::= { hwLocationProfileEntry 9 }

		 --1.3.6.1.4.1.2011.6.139.11.1.43.1.10
		hwLocationEkahauServerIPv6Address OBJECT-TYPE
			SYNTAX OCTET STRING
			MAX-ACCESS read-write
			STATUS current
			DESCRIPTION 
				"This object indicates the IPv6 address of the location server for Ekahau tag location."
			::= { hwLocationProfileEntry 10 }

		 --1.3.6.1.4.1.2011.6.139.11.1.43.1.11
		hwLocationEkahauServerPort OBJECT-TYPE
			SYNTAX Unsigned32 (0|1024..65535)
			MAX-ACCESS read-write
			STATUS current
			DESCRIPTION 
				"This object indicates the port number of the location server for Ekahau tag location."
			::= { hwLocationProfileEntry 11 }

		 --1.3.6.1.4.1.2011.6.139.11.1.43.1.12
		hwLocationEkahauViaACEnable OBJECT-TYPE
			SYNTAX INTEGER
				{
				disable(1) ,
				enable(2)
				}
			MAX-ACCESS read-write
			STATUS current
			DESCRIPTION 
				"This object indicates whether Ekahau tag location data is reported to the AC."
			::= { hwLocationProfileEntry 12 }

		 --1.3.6.1.4.1.2011.6.139.11.1.43.1.13
		hwLocationEkahauViaACPort OBJECT-TYPE
			SYNTAX Unsigned32 (0|1024..65535)
			MAX-ACCESS read-write
			STATUS current
			DESCRIPTION 
				"This object indicates that Ekahau location data is reported to the AC that forwards the data to the AE. A port is configured for the AP to report location data to the AC."
			::= { hwLocationProfileEntry 13 }

		 --1.3.6.1.4.1.2011.6.139.11.1.43.1.14
		hwLocationSourceIPAddress OBJECT-TYPE
			SYNTAX IpAddress
			MAX-ACCESS read-write
			STATUS current
			DESCRIPTION 
				"This object indicates the source IPv4 address for reporting location data in AeroScout or Ekahau location mode. You choose an IPv4 or IPv6 address."
			::= { hwLocationProfileEntry 14 }

		 --1.3.6.1.4.1.2011.6.139.11.1.43.1.15
		hwLocationSourceIPv6Address OBJECT-TYPE
			SYNTAX OCTET STRING
			MAX-ACCESS read-write
			STATUS current
			DESCRIPTION 
				"This object indicates the source IPv6 address for reporting location data in AeroScout or Ekahau location mode. You choose an IPv4 or IPv6 address."
			::= { hwLocationProfileEntry 15 }

		 --1.3.6.1.4.1.2011.6.139.11.1.43.1.16
		hwLocationPrivateMuEnable OBJECT-TYPE
			SYNTAX INTEGER
				{
				disable(1) ,
				enable(2)
				}
			MAX-ACCESS read-write
			STATUS current
			DESCRIPTION 
				"This object indicates the status of the Huawei proprietary terminal location function. The default value is 1."
			::= { hwLocationProfileEntry 16 }

		 --1.3.6.1.4.1.2011.6.139.11.1.43.1.17
		hwLocationPrivateServerIPAddress OBJECT-TYPE
			SYNTAX IpAddress
			MAX-ACCESS read-write
			STATUS current
			DESCRIPTION 
				"This object indicates the IP address of the server for the Huawei proprietary location function."
			::= { hwLocationProfileEntry 17 }

		 --1.3.6.1.4.1.2011.6.139.11.1.43.1.18
		hwLocationPrivateServerIPv6Address OBJECT-TYPE
			SYNTAX OCTET STRING
			MAX-ACCESS read-write
			STATUS current
			DESCRIPTION 
				"This object indicates the IPv6 address of the server for the Huawei proprietary location function."
			::= { hwLocationProfileEntry 18 }

		 --1.3.6.1.4.1.2011.6.139.11.1.43.1.19
		hwLocationPrivateServerPort OBJECT-TYPE
			SYNTAX Unsigned32 (0|5000..65535)
			MAX-ACCESS read-write
			STATUS current
			DESCRIPTION 
				"This object indicates the port number of the server for the Huawei proprietary location function."
			::= { hwLocationProfileEntry 19 }

		 --1.3.6.1.4.1.2011.6.139.11.1.43.1.20
		hwLocationPrivateViaACEnable OBJECT-TYPE
			SYNTAX INTEGER
				{
				disable(1) ,
				enable(2)
				}
			MAX-ACCESS read-write
			STATUS current
			DESCRIPTION 
				"This object indicates whether Huawei proprietary terminal location data is reported to the AC. The default value is 2.1: Enable2: Disable"
			::= { hwLocationProfileEntry 20 }

		 --1.3.6.1.4.1.2011.6.139.11.1.43.1.21
		hwLocationPrivateViaACPort OBJECT-TYPE
			SYNTAX Unsigned32 (0|5000..65535)
			MAX-ACCESS read-write
			STATUS current
			DESCRIPTION 
				"This object indicates that Huawei proprietary terminal location data is reported to the AC that forwards the data to the location server. A port is configured for the AP to report location data to the AC.
The default destination IP address and port number to which the AP reports terminal location data is the AC's IP address and 6411 respectively."
			::= { hwLocationProfileEntry 21 }

		 --1.3.6.1.4.1.2011.6.139.11.1.43.1.22
		hwLocationPrivateReportFrequency OBJECT-TYPE
			SYNTAX Unsigned32 (500..60000)
			MAX-ACCESS read-write
			STATUS current
			DESCRIPTION 
				"This object indicates the interval for the AP to report location data in Huawei proprietary terminal location mode. The default value is 20000 ms."
			::= { hwLocationProfileEntry 22 }

		 --1.3.6.1.4.1.2011.6.139.11.1.43.1.23
		hwLocationProfileRowStatus OBJECT-TYPE
			SYNTAX RowStatus
			MAX-ACCESS read-write
			STATUS current
			DESCRIPTION 
				"This object indicates the row status of this table. ROWSTATUS_CREATEANDFLOW and ROWSTATUS_DESTROY are commonly used.ROWSTATUS_UNDEFINED: undefinedROWSTATUS_ACTIVE: activeROWSTATUS_NOTINSERVICE: notInServiceROWSTATUS_NOTREADY: notReadyROWSTATUS_CREATEANDFLOW: createAndGoROWSTATUS_CREATEANDWAIT: createAndWaitROWSTATUS_DESTROY: destroy"
			::= { hwLocationProfileEntry 23 }

			
		-- 1.3.6.1.4.1.2011.6.139.11.1.45
		hwHotspot2ProfileTable OBJECT-TYPE
			SYNTAX SEQUENCE OF HwHotspot2ProfileEntry 
			MAX-ACCESS not-accessible
			STATUS current
			DESCRIPTION 
				"This table is used to configure and query Hotspot2.0 profile parameters."
			::= { hwWlanConfigObjects 45 }

		--1.3.6.1.4.1.2011.6.139.11.1.45.1
		hwHotspot2ProfileEntry OBJECT-TYPE
			SYNTAX HwHotspot2ProfileEntry 
			MAX-ACCESS not-accessible
			STATUS current
			DESCRIPTION 
				"The index of this table is hwHotspot2ProfileName."
			INDEX { hwHotspot2ProfileName }
			::= { hwHotspot2ProfileTable 1 }


		HwHotspot2ProfileEntry ::=
			SEQUENCE {				
				hwHotspot2ProfileName
					OCTET STRING,
				hwHotspot2NetworkType
					Unsigned32,
				hwHotspot2InternetAccess
					INTEGER,
				hwHotspot2VenueGroupCode
					Unsigned32,
				hwHotspot2VenueTypeCode
					Unsigned32,
				hwHotspot2Hessid
					MacAddress,
				hwHotspot2IPv4AddressAvail
					Unsigned32,
				hwHotspot2IPv6AddressAvail
					Unsigned32,
				hwHotspot2NetworkAuthenType
					Unsigned32,
				hwHotspot2RedirectUrl
					OCTET STRING,
				hwHotspot2CarryP2PCrossConnectInfo
					INTEGER,
				hwHotspot2CellularNetworkProfile
					OCTET STRING,
				hwHotspot2ConnectionCapabilityProfile
					OCTET STRING,
				hwHotspot2OperatorNameProfile
					OCTET STRING,
				hwHotspot2OperatingClassProfile
					OCTET STRING,
				hwHotspot2OperatorDomainProfile
					OCTET STRING,
				hwHotspot2NaiRealmProfile
					OCTET STRING,
				hwHotspot2VenueNameProfile
					OCTET STRING,
				hwHotspot2RoamingConsortiumProfile
					OCTET STRING,
				hwHotspot2ProfileRowStatus
					RowStatus 
			 }

		 --1.3.6.1.4.1.2011.6.139.11.1.45.1.1
		hwHotspot2ProfileName OBJECT-TYPE
			SYNTAX OCTET STRING (SIZE (1..35))
			MAX-ACCESS not-accessible
			STATUS current
			DESCRIPTION 
				"This object indicates the name of a Hotspot2.0 profile. It is the index of the table."
			::= { hwHotspot2ProfileEntry 1 }

		 --1.3.6.1.4.1.2011.6.139.11.1.45.1.2
		hwHotspot2NetworkType OBJECT-TYPE
			SYNTAX Unsigned32 (0..1|2..3|4..5|14..15)
			MAX-ACCESS read-write
			STATUS current
			DESCRIPTION 
				"This object indicates that the network type is an interworking information element. This configuration is mandatory. The AP adds this information to Beacon and Probe Response packets, which indicates network types, to assist users in discovering and selecting networks. The default value is 15.0: Private-network1: private-guest2: public-chargeable3: public-free4: personal-device5: emergency-service14: Test15: Wildcard"
			::= { hwHotspot2ProfileEntry 2 }

		 --1.3.6.1.4.1.2011.6.139.11.1.45.1.3
		hwHotspot2InternetAccess OBJECT-TYPE
			SYNTAX INTEGER
				{
				allowAcess(1),
				unallowedAcess(2)
				}
			MAX-ACCESS read-write
			STATUS current
			DESCRIPTION 
				"This object indicates that the Internet attribute is an interworking information element. This configuration is mandatory. The AP adds this information to Beacon and Probe Response packets, which indicates whether users are allowed to access the Internet, to assist users in discovering and selecting networks. The default value is 2."
			::= { hwHotspot2ProfileEntry 3 }

		 --1.3.6.1.4.1.2011.6.139.11.1.45.1.4
		hwHotspot2VenueGroupCode OBJECT-TYPE
			SYNTAX Unsigned32 (0..255|4294967295)
			MAX-ACCESS read-write
			STATUS current
			DESCRIPTION 
				"For details, see Table 7-25m-Venue Group codes and descriptions in the 802.11u protocol.
The default value 0xFFFFFFFF indicates that no configuration is added."
			::= { hwHotspot2ProfileEntry 4 }

		 --1.3.6.1.4.1.2011.6.139.11.1.45.1.5
		hwHotspot2VenueTypeCode OBJECT-TYPE
			SYNTAX Unsigned32 (0..255|4294967295)
			MAX-ACCESS read-write
			STATUS current
			DESCRIPTION 
				"For details, see Table 7-25n-Venue Type assignments in the 802.11u protocol.
The default value 0xFFFFFFFF indicates that no configuration is added."
			::= { hwHotspot2ProfileEntry 5 }

		 --1.3.6.1.4.1.2011.6.139.11.1.45.1.6
		hwHotspot2Hessid OBJECT-TYPE
			SYNTAX MacAddress
			MAX-ACCESS read-write
			STATUS current
			DESCRIPTION 
				"This object indicates the HESSID of a hot spot network. The default value is null, indicating that no configuration is added."
			::= { hwHotspot2ProfileEntry 6 }

		 --1.3.6.1.4.1.2011.6.139.11.1.45.1.7
		hwHotspot2IPv4AddressAvail OBJECT-TYPE
			SYNTAX Unsigned32 (0..7|4294967295)
			MAX-ACCESS read-write
			STATUS current
			DESCRIPTION 
				"This object indicates available types of IPv4 addresses. 8 to 63 are reserved. The default value 0xFFFFFFFF indicates that no configuration is added.0: Address type not available.1: Public IPv4 address available,2: Port-restricted IPv4 address available,3: Single NATed private IPv4 address available,4: Double NATed private IPv4 address available,5: Port-restricted IPv4 address and single NATed IPv4 address available,6: Port-restricted IPv4 address and double NATed IPv4 address available,7: Availability of the address type is not known,8 to 63: Reserved"
			::= { hwHotspot2ProfileEntry 7 }

		 --1.3.6.1.4.1.2011.6.139.11.1.45.1.8
		hwHotspot2IPv6AddressAvail OBJECT-TYPE
			SYNTAX Unsigned32 (0..2|4294967295)
			MAX-ACCESS read-write
			STATUS current
			DESCRIPTION 
				"This object indicates available types of IPv4 addresses. 3 is reserved. The default value 0xFFFFFFFF indicates that no configuration is added.0: Address type not available1: Address type available2: Availability of the address type not known3: Reserved"
			::= { hwHotspot2ProfileEntry 8 }

		 --1.3.6.1.4.1.2011.6.139.11.1.45.1.9
		hwHotspot2NetworkAuthenType OBJECT-TYPE
			SYNTAX Unsigned32 (0..3|4294967295)
			MAX-ACCESS read-write
			STATUS current
			DESCRIPTION 
				"This object indicates the network authentication type. 4 to 255 are reserved. The default value 0xFFFFFFFF indicates that no configuration is added.0: Acceptance of terms and conditions.1: On-line enrollment supported,2: http/https redirection,3: DNS redirection,4 to 255: Reserved"
			::= { hwHotspot2ProfileEntry 9 }

		 --1.3.6.1.4.1.2011.6.139.11.1.45.1.10
		hwHotspot2RedirectUrl OBJECT-TYPE
			SYNTAX OCTET STRING (SIZE (0..255))
			MAX-ACCESS read-write
			STATUS current
			DESCRIPTION 
				"This object indicates the redirection URL.This parameter is optional when Network Authentication Type is set to acceptance.This parameter is mandatory when Network Authentication Type is set to http-https-redirection.This parameter is not configurable when Network Authentication Type is set to other values."
			::= { hwHotspot2ProfileEntry 10 }

		 --1.3.6.1.4.1.2011.6.139.11.1.45.1.11
		hwHotspot2CarryP2PCrossConnectInfo OBJECT-TYPE
			SYNTAX INTEGER
				{
				disable(1) ,
				enable(2)
				}
			MAX-ACCESS read-write
			STATUS current
			DESCRIPTION 
				"This object indicates whether hot spot networks allow P2P devices to set up cross connections. Currently, this function is not supported. The default value is 1."
			::= { hwHotspot2ProfileEntry 11 }

		 --1.3.6.1.4.1.2011.6.139.11.1.45.1.12
		hwHotspot2CellularNetworkProfile OBJECT-TYPE
			SYNTAX OCTET STRING (SIZE (0..35))
			MAX-ACCESS read-write
			STATUS current
			DESCRIPTION 
				"This object indicates the bound cellular network profile. By default, no cellular network profile is bound."
			::= { hwHotspot2ProfileEntry 12 }

		 --1.3.6.1.4.1.2011.6.139.11.1.45.1.13
		hwHotspot2ConnectionCapabilityProfile OBJECT-TYPE
			SYNTAX OCTET STRING (SIZE (0..35))
			MAX-ACCESS read-write
			STATUS current
			DESCRIPTION 
				"This object indicates the bound connection capability profile. By default, no connection capability profile is bound."
			::= { hwHotspot2ProfileEntry 13 }

		 --1.3.6.1.4.1.2011.6.139.11.1.45.1.14
		hwHotspot2OperatorNameProfile OBJECT-TYPE
			SYNTAX OCTET STRING (SIZE (0..35))
			MAX-ACCESS read-write
			STATUS current
			DESCRIPTION 
				"This object indicates the bound operator name profile. By default, no operator name profile is bound."
			::= { hwHotspot2ProfileEntry 14 }

		 --1.3.6.1.4.1.2011.6.139.11.1.45.1.15
		hwHotspot2OperatingClassProfile OBJECT-TYPE
			SYNTAX OCTET STRING (SIZE (0..35))
			MAX-ACCESS read-write
			STATUS current
			DESCRIPTION 
				"This object indicates the bound operating class profile. By default, no operating class profile is bound."
			::= { hwHotspot2ProfileEntry 15 }

		 --1.3.6.1.4.1.2011.6.139.11.1.45.1.16
		hwHotspot2OperatorDomainProfile OBJECT-TYPE
			SYNTAX OCTET STRING (SIZE (0..35))
			MAX-ACCESS read-write
			STATUS current
			DESCRIPTION 
				"This object indicates the bound operator domain profile. By default, no operator domain profile is bound."
			::= { hwHotspot2ProfileEntry 16 }

		 --1.3.6.1.4.1.2011.6.139.11.1.45.1.17
		hwHotspot2NaiRealmProfile OBJECT-TYPE
			SYNTAX OCTET STRING (SIZE (0..35))
			MAX-ACCESS read-write
			STATUS current
			DESCRIPTION 
				"This object indicates the bound NAI realm profile. By default, no NAI realm profile is bound."
			::= { hwHotspot2ProfileEntry 17 }

		 --1.3.6.1.4.1.2011.6.139.11.1.45.1.18
		hwHotspot2VenueNameProfile OBJECT-TYPE
			SYNTAX OCTET STRING (SIZE (0..35))
			MAX-ACCESS read-write
			STATUS current
			DESCRIPTION 
				"This object indicates the bound venue name profile. By default, no venue name profile is bound."
			::= { hwHotspot2ProfileEntry 18 }

		 --1.3.6.1.4.1.2011.6.139.11.1.45.1.19
		hwHotspot2RoamingConsortiumProfile OBJECT-TYPE
			SYNTAX OCTET STRING (SIZE (0..35))
			MAX-ACCESS read-write
			STATUS current
			DESCRIPTION 
				"This object indicates the bound roaming consortium profile. By default, no roaming consortium profile is bound."
			::= { hwHotspot2ProfileEntry 19 }

		 --1.3.6.1.4.1.2011.6.139.11.1.45.1.20
		hwHotspot2ProfileRowStatus OBJECT-TYPE
			SYNTAX RowStatus
			MAX-ACCESS read-write
			STATUS current
			DESCRIPTION 
				"This object indicates the row status of this table. ROWSTATUS_CREATEANDFLOW and ROWSTATUS_DESTROY are commonly used.ROWSTATUS_UNDEFINED: undefinedROWSTATUS_ACTIVE: activeROWSTATUS_NOTINSERVICE: notInServiceROWSTATUS_NOTREADY: notReadyROWSTATUS_CREATEANDFLOW: createAndGoROWSTATUS_CREATEANDWAIT: createAndWaitROWSTATUS_DESTROY: destroy"
			::= { hwHotspot2ProfileEntry 20 }

		--1.3.6.1.4.1.2011.6.139.11.1.46
		hwCellularNetworkProfileTable OBJECT-TYPE
			SYNTAX SEQUENCE OF HwCellularNetworkProfileEntry 
			MAX-ACCESS not-accessible
			STATUS current
			DESCRIPTION 
				"This table is used to configure and query cellular network profile parameters."
			::= { hwWlanConfigObjects 46 }

		--1.3.6.1.4.1.2011.6.139.11.1.46.1
		hwCellularNetworkProfileEntry OBJECT-TYPE
			SYNTAX HwCellularNetworkProfileEntry 
			MAX-ACCESS not-accessible
			STATUS current
			DESCRIPTION 
				"The index of this table is hwCellularNetworkProfileName."
			INDEX { hwCellularNetworkProfileName }
			::= { hwCellularNetworkProfileTable 1 }


		HwCellularNetworkProfileEntry ::=
			SEQUENCE {				
				hwCellularNetworkProfileName
					OCTET STRING,
				hwCellularNetworkProfilePlmnIDList
					OCTET STRING,
				hwCellularNetworkProfileRowStatus
					RowStatus 
			 }

		 --1.3.6.1.4.1.2011.6.139.11.1.46.1.1
		hwCellularNetworkProfileName OBJECT-TYPE
			SYNTAX OCTET STRING (SIZE (1..35))
			MAX-ACCESS not-accessible
			STATUS current
			DESCRIPTION 
				"This object indicates the name of a cellular network profile. It is the index of the table."
			::= { hwCellularNetworkProfileEntry 1 }

		 --1.3.6.1.4.1.2011.6.139.11.1.46.1.2
		hwCellularNetworkProfilePlmnIDList OBJECT-TYPE
			SYNTAX OCTET STRING (SIZE (0..255))
			MAX-ACCESS read-write
			STATUS current
			DESCRIPTION 
				"NOTE By default, no configuration is added.PLMNs are separated by question marks (?).A maximum of 32 PLMNs can be configured.A PLMN is a 5-digit or 6-digit numeric string."
			::= { hwCellularNetworkProfileEntry 2 }

		 --1.3.6.1.4.1.2011.6.139.11.1.46.1.3
		hwCellularNetworkProfileRowStatus OBJECT-TYPE
			SYNTAX RowStatus
			MAX-ACCESS read-write
			STATUS current
			DESCRIPTION 
				"This object indicates the row status of this table. createAndGo(4) and destroy(6) are commonly used."
			::= { hwCellularNetworkProfileEntry 3 }

		--1.3.6.1.4.1.2011.6.139.11.1.47
		hwConnectionCapabilityProfileTable OBJECT-TYPE
			SYNTAX SEQUENCE OF HwConnectionCapabilityProfileEntry 
			MAX-ACCESS not-accessible
			STATUS current
			DESCRIPTION 
				"This table is used to configure and query connection capability profile parameters."
			::= { hwWlanConfigObjects 47 }

		--1.3.6.1.4.1.2011.6.139.11.1.47.1
		hwConnectionCapabilityProfileEntry OBJECT-TYPE
			SYNTAX HwConnectionCapabilityProfileEntry 
			MAX-ACCESS not-accessible
			STATUS current
			DESCRIPTION 
				"The index of this table is hwConnectionCapabilityProfileName."
			INDEX { hwConnectionCapabilityProfileName }
			::= { hwConnectionCapabilityProfileTable 1 }


		HwConnectionCapabilityProfileEntry ::=
			SEQUENCE {				
				hwConnectionCapabilityProfileName
					OCTET STRING,
				hwConnectionCapabilityEsp
					INTEGER,
				hwConnectionCapabilityIcmp
					INTEGER,
				hwConnectionCapabilityTcpFtp
					INTEGER,
				hwConnectionCapabilityTcpHttp
					INTEGER,
				hwConnectionCapabilityTcpPptpVpn
					INTEGER,
				hwConnectionCapabilityTcpSsh
					INTEGER,
				hwConnectionCapabilityTcpTlsVpn
					INTEGER,
				hwConnectionCapabilityTcpVoip
					INTEGER,
				hwConnectionCapabilityUdpIke2Port4500
					INTEGER,
				hwConnectionCapabilityUdpIke2Port500
					INTEGER,
				hwConnectionCapabilityUdpVoip
					INTEGER,
				hwConnectionCapabilityProfileRowStatus
					RowStatus 
			 }

		 --1.3.6.1.4.1.2011.6.139.11.1.47.1.1
		hwConnectionCapabilityProfileName OBJECT-TYPE
			SYNTAX OCTET STRING (SIZE (1..35))
			MAX-ACCESS not-accessible
			STATUS current
			DESCRIPTION 
				"This object indicates the name of a connection capability profile. It is the index of the table."
			::= { hwConnectionCapabilityProfileEntry 1 }

		 --1.3.6.1.4.1.2011.6.139.11.1.47.1.2
		hwConnectionCapabilityEsp OBJECT-TYPE
			SYNTAX INTEGER
				{
				unknown(1),
				on(2),
				off(3)
				}
			MAX-ACCESS read-write
			STATUS current
			DESCRIPTION 
				"This object indicates whether ESP is supported.
The default value is unknown(1)."
			::= { hwConnectionCapabilityProfileEntry 2 }

		 --1.3.6.1.4.1.2011.6.139.11.1.47.1.3
		hwConnectionCapabilityIcmp OBJECT-TYPE
			SYNTAX INTEGER
				{
				unknown(1),
				on(2),
				off(3)
				}
			MAX-ACCESS read-write
			STATUS current
			DESCRIPTION 
				"This object indicates whether ICMP is supported.
The default value is unknown(1)."
			::= { hwConnectionCapabilityProfileEntry 3 }

		 --1.3.6.1.4.1.2011.6.139.11.1.47.1.4
		hwConnectionCapabilityTcpFtp OBJECT-TYPE
			SYNTAX INTEGER
				{
				unknown(1),
				on(2),
				off(3)
				}
			MAX-ACCESS read-write
			STATUS current
			DESCRIPTION 
				"This object indicates whether FTP(TCP) is supported.
The default value is unknown(1)."
			::= { hwConnectionCapabilityProfileEntry 4 }

		 --1.3.6.1.4.1.2011.6.139.11.1.47.1.5
		hwConnectionCapabilityTcpHttp OBJECT-TYPE
			SYNTAX INTEGER
				{
				unknown(1),
				on(2),
				off(3)
				}
			MAX-ACCESS read-write
			STATUS current
			DESCRIPTION 
				"This object indicates whether HTTP (port 80) is supported.
The default value is unknown(1)."
			::= { hwConnectionCapabilityProfileEntry 5 }

		 --1.3.6.1.4.1.2011.6.139.11.1.47.1.6
		hwConnectionCapabilityTcpPptpVpn OBJECT-TYPE
			SYNTAX INTEGER
				{
				unknown(1),
				on(2),
				off(3)
				}
			MAX-ACCESS read-write
			STATUS current
			DESCRIPTION 
				"This object indicates whether PPTP for VPN services (port 1723) is supported.
The default value is unknown(1)."
			::= { hwConnectionCapabilityProfileEntry 6 }

		 --1.3.6.1.4.1.2011.6.139.11.1.47.1.7
		hwConnectionCapabilityTcpSsh OBJECT-TYPE
			SYNTAX INTEGER
				{
				unknown(1),
				on(2),
				off(3)
				}
			MAX-ACCESS read-write
			STATUS current
			DESCRIPTION 
				"This object indicates whether SSH is supported.
The default value is unknown(1)."
			::= { hwConnectionCapabilityProfileEntry 7 }

		 --1.3.6.1.4.1.2011.6.139.11.1.47.1.8
		hwConnectionCapabilityTcpTlsVpn OBJECT-TYPE
			SYNTAX INTEGER
				{
				unknown(1),
				on(2),
				off(3)
				}
			MAX-ACCESS read-write
			STATUS current
			DESCRIPTION 
				"This object indicates whether TLS VPN (port 443) is supported.
The default value is unknown(1)."
			::= { hwConnectionCapabilityProfileEntry 8 }

		 --1.3.6.1.4.1.2011.6.139.11.1.47.1.9
		hwConnectionCapabilityTcpVoip OBJECT-TYPE
			SYNTAX INTEGER
				{
				unknown(1),
				on(2),
				off(3)
				}
			MAX-ACCESS read-write
			STATUS current
			DESCRIPTION 
				"This object indicates whether VoIP (port 5060) is supported.
The default value is unknown(1)."
			::= { hwConnectionCapabilityProfileEntry 9 }

		 --1.3.6.1.4.1.2011.6.139.11.1.47.1.10
		hwConnectionCapabilityUdpIke2Port4500 OBJECT-TYPE
			SYNTAX INTEGER
				{
				unknown(1),
				on(2),
				off(3)
				}
			MAX-ACCESS read-write
			STATUS current
			DESCRIPTION 
				"This object indicates whether IKEv2 (port 4500) is supported.
The default value is unknown(1)."
			::= { hwConnectionCapabilityProfileEntry 10 }

		 --1.3.6.1.4.1.2011.6.139.11.1.47.1.11
		hwConnectionCapabilityUdpIke2Port500 OBJECT-TYPE
			SYNTAX INTEGER
				{
				unknown(1),
				on(2),
				off(3)
				}
			MAX-ACCESS read-write
			STATUS current
			DESCRIPTION 
				"This object indicates whether IKEv2 (port 500) is supported.
The default value is unknown(1)."
			::= { hwConnectionCapabilityProfileEntry 11 }

		 --1.3.6.1.4.1.2011.6.139.11.1.47.1.12
		hwConnectionCapabilityUdpVoip OBJECT-TYPE
			SYNTAX INTEGER
				{
				unknown(1),
				on(2),
				off(3)
				}
			MAX-ACCESS read-write
			STATUS current
			DESCRIPTION 
				"This object indicates whether VoIP (port 5060) is supported.
The default value is unknown(1)."
			::= { hwConnectionCapabilityProfileEntry 12 }

		 --1.3.6.1.4.1.2011.6.139.11.1.47.1.13
		hwConnectionCapabilityProfileRowStatus OBJECT-TYPE
			SYNTAX RowStatus
			MAX-ACCESS read-write
			STATUS current
			DESCRIPTION 
				"This object indicates the row status of this table. createAndGo(4) and destroy(6) are commonly used."
			::= { hwConnectionCapabilityProfileEntry 13 }

		--1.3.6.1.4.1.2011.6.139.11.1.48
		hwOperatorNameProfileTable OBJECT-TYPE
			SYNTAX SEQUENCE OF HwOperatorNameProfileEntry 
			MAX-ACCESS not-accessible
			STATUS current
			DESCRIPTION 
				"This table is used to configure and query operator name profile parameters."
			::= { hwWlanConfigObjects 48 }

		--1.3.6.1.4.1.2011.6.139.11.1.48.1
		hwOperatorNameProfileEntry OBJECT-TYPE
			SYNTAX HwOperatorNameProfileEntry 
			MAX-ACCESS not-accessible
			STATUS current
			DESCRIPTION 
				"The index of this table is hwOperatorNameProfileName."
			INDEX { hwOperatorNameProfileName }
			::= { hwOperatorNameProfileTable 1 }


		HwOperatorNameProfileEntry ::=
			SEQUENCE {				
				hwOperatorNameProfileName
					OCTET STRING,
				hwOperatorNameLanguageCodeList
					OCTET STRING,
				hwOperatorFriendlyNameList
					OCTET STRING,
				hwOperatorNameProfileRowStatus
					RowStatus 
			 }

		 --1.3.6.1.4.1.2011.6.139.11.1.48.1.1
		hwOperatorNameProfileName OBJECT-TYPE
			SYNTAX OCTET STRING (SIZE (1..35))
			MAX-ACCESS not-accessible
			STATUS current
			DESCRIPTION 
				"This object indicates the name of an operator name profile. It is the index of the table."
			::= { hwOperatorNameProfileEntry 1 }

		 --1.3.6.1.4.1.2011.6.139.11.1.48.1.2
		hwOperatorNameLanguageCodeList OBJECT-TYPE
			SYNTAX OCTET STRING (SIZE (0..256))
			MAX-ACCESS read-write
			STATUS current
			DESCRIPTION 
				"A value of LanguageCode indicates a language. It is a string of 2-3 characters.
chi/zho/zh indicates Chinese and eng/en indicates English.
NOTE By default, no configuration is added.Values of LanguageCode are separated by question marks (?).A maximum of 32 LanguageCode values can be configured.A LanguageCode value must match a FriendlyName value."
			::= { hwOperatorNameProfileEntry 2 }

		 --1.3.6.1.4.1.2011.6.139.11.1.48.1.3
		hwOperatorFriendlyNameList OBJECT-TYPE
			SYNTAX OCTET STRING (SIZE (0..2048))
			MAX-ACCESS read-write
			STATUS current
			DESCRIPTION 
				"NOTE By default, no configuration is added.A FriendlyName value is a string of 1-32 characters. FriendlyName values are separated by question marks (?).A maximum of 32 FriendlyName values can be configured.A LanguageCode value must match a FriendlyName value."
			::= { hwOperatorNameProfileEntry 3 }

		 --1.3.6.1.4.1.2011.6.139.11.1.48.1.4
		hwOperatorNameProfileRowStatus OBJECT-TYPE
			SYNTAX RowStatus
			MAX-ACCESS read-write
			STATUS current
			DESCRIPTION 
				"This object indicates the row status of this table. createAndGo(4) and destroy(6) are commonly used."
			::= { hwOperatorNameProfileEntry 4 }

		--1.3.6.1.4.1.2011.6.139.11.1.49
		hwOperatorClassProfileTable OBJECT-TYPE
			SYNTAX SEQUENCE OF HwOperatorClassProfileEntry 
			MAX-ACCESS not-accessible
			STATUS current
			DESCRIPTION 
				"This table is used to configure operating class profile parameters."
			::= { hwWlanConfigObjects 49 }

		--1.3.6.1.4.1.2011.6.139.11.1.49.1
		hwOperatorClassProfileEntry OBJECT-TYPE
			SYNTAX HwOperatorClassProfileEntry 
			MAX-ACCESS not-accessible
			STATUS current
			DESCRIPTION 
				"The index of this table is hwOperatorClassProfileName."
			INDEX { hwOperatorClassProfileName }
			::= { hwOperatorClassProfileTable 1 }


		HwOperatorClassProfileEntry ::=
			SEQUENCE {				
				hwOperatorClassProfileName
					OCTET STRING,
				hwOperatorClassIndicationList
					OCTET STRING,
				hwOperatorClassProfileRowStatus
					RowStatus 
			 }

		 --1.3.6.1.4.1.2011.6.139.11.1.49.1.1
		hwOperatorClassProfileName OBJECT-TYPE
			SYNTAX OCTET STRING (SIZE (1..35))
			MAX-ACCESS not-accessible
			STATUS current
			DESCRIPTION 
				"This object indicates the name of an operating class profile profile. It is the index of the table."
			::= { hwOperatorClassProfileEntry 1 }

		 --1.3.6.1.4.1.2011.6.139.11.1.49.1.2
		hwOperatorClassIndicationList OBJECT-TYPE
			SYNTAX OCTET STRING (SIZE (0..256))
			MAX-ACCESS read-write
			STATUS current
			DESCRIPTION 
				"NOTE By default, no configuration is added.A value of OperatorClassIndication is an integer that ranges from 1 to 255.A maximum of 32 OperatorClassIndication values can be configured."
			::= { hwOperatorClassProfileEntry 2 }

		 --1.3.6.1.4.1.2011.6.139.11.1.49.1.3
		hwOperatorClassProfileRowStatus OBJECT-TYPE
			SYNTAX RowStatus
			MAX-ACCESS read-write
			STATUS current
			DESCRIPTION 
				"This object indicates the row status of this table. createAndGo(4) and destroy(6) are commonly used."
			::= { hwOperatorClassProfileEntry 3 }

		--1.3.6.1.4.1.2011.6.139.11.1.50
		hwOperatorDomainNameProfileTable OBJECT-TYPE
			SYNTAX SEQUENCE OF HwOperatorDomainNameProfileEntry 
			MAX-ACCESS not-accessible
			STATUS current
			DESCRIPTION 
				"This table is used to configure and query operator domain profile parameters."
			::= { hwWlanConfigObjects 50 }

		--1.3.6.1.4.1.2011.6.139.11.1.50.1
		hwOperatorDomainNameProfileEntry OBJECT-TYPE
			SYNTAX HwOperatorDomainNameProfileEntry 
			MAX-ACCESS not-accessible
			STATUS current
			DESCRIPTION 
				"The index of this table is hwOperatorDomainNameProfileName."
			INDEX { hwOperatorDomainNameProfileName }
			::= { hwOperatorDomainNameProfileTable 1 }


		HwOperatorDomainNameProfileEntry ::=
			SEQUENCE {				
				hwOperatorDomainNameProfileName
					OCTET STRING,
				hwOperatorDomainNameList
					OCTET STRING,
				hwOperatorDomainNameProfileRowStatus
					RowStatus 
			 }

		 --1.3.6.1.4.1.2011.6.139.11.1.50.1.1
		hwOperatorDomainNameProfileName OBJECT-TYPE
			SYNTAX OCTET STRING (SIZE (1..35))
			MAX-ACCESS not-accessible
			STATUS current
			DESCRIPTION 
				"This object indicates the name of an operating class profile profile. It is the index of the table."
			::= { hwOperatorDomainNameProfileEntry 1 }

		 --1.3.6.1.4.1.2011.6.139.11.1.50.1.2
		hwOperatorDomainNameList OBJECT-TYPE
			SYNTAX OCTET STRING (SIZE (0..2048))
			MAX-ACCESS read-write
			STATUS current
			DESCRIPTION 
				"NOTE By default, no configuration is added.A DomainName value is a string of 1-64 characters in compliance with RFC1035.DomainName values are separated by question marks (?).A maximum of 32 DomainName values can be configured."
			::= { hwOperatorDomainNameProfileEntry 2 }

		 --1.3.6.1.4.1.2011.6.139.11.1.50.1.3
		hwOperatorDomainNameProfileRowStatus OBJECT-TYPE
			SYNTAX RowStatus
			MAX-ACCESS read-write
			STATUS current
			DESCRIPTION 
				"This object indicates the row status of this table. createAndGo(4) and destroy(6) are commonly used."
			::= { hwOperatorDomainNameProfileEntry 3 }

		--1.3.6.1.4.1.2011.6.139.11.1.51
		hwNAIRealmProfileTable OBJECT-TYPE
			SYNTAX SEQUENCE OF HwNAIRealmProfileEntry 
			MAX-ACCESS not-accessible
			STATUS current
			DESCRIPTION 
				"This table is used to configure and query NAI realm profile parameters."
			::= { hwWlanConfigObjects 51 }

		--1.3.6.1.4.1.2011.6.139.11.1.51.1
		hwNAIRealmProfileEntry OBJECT-TYPE
			SYNTAX HwNAIRealmProfileEntry 
			MAX-ACCESS not-accessible
			STATUS current
			DESCRIPTION 
				"Indexes of this table are hwNAIRealmProfileName, hwNAIRealmName, hwNAIRealmEapMethodType, and hwNAIRealmEapAuthenID."
			INDEX { hwNAIRealmProfileName,hwNAIRealmName,hwNAIRealmEapMethodType,hwNAIRealmEapAuthenID }
			::= { hwNAIRealmProfileTable 1 }


		HwNAIRealmProfileEntry ::=
			SEQUENCE {				
				hwNAIRealmProfileName
					OCTET STRING,
				hwNAIRealmName
					OCTET STRING,
				hwNAIRealmEapMethodType
					Unsigned32,
				hwNAIRealmEapAuthenID
					Unsigned32,
				hwNAIRealmEapAuthenPara
					Unsigned32,
				hwNAIRealmProfileRowStatus
					RowStatus
			 }

		 --1.3.6.1.4.1.2011.6.139.11.1.51.1.1
		hwNAIRealmProfileName OBJECT-TYPE
			SYNTAX OCTET STRING (SIZE (1..35))
			MAX-ACCESS not-accessible
			STATUS current
			DESCRIPTION 
				"This object indicates the name of a NAI realm profile. It is the index of the table."
			::= { hwNAIRealmProfileEntry 1 }

		 --1.3.6.1.4.1.2011.6.139.11.1.51.1.2
		hwNAIRealmName OBJECT-TYPE
			SYNTAX OCTET STRING (SIZE (0..63))
			MAX-ACCESS not-accessible
			STATUS current
			DESCRIPTION 
				"This object indicates a network identifier."
			::= { hwNAIRealmProfileEntry 2 }

		 --1.3.6.1.4.1.2011.6.139.11.1.51.1.3
		hwNAIRealmEapMethodType OBJECT-TYPE
			SYNTAX Unsigned32 (0..255 | 4294967295)
			MAX-ACCESS not-accessible
			STATUS current
			DESCRIPTION 
				"This object indicates the authorization type.
The default value is 0xffffffff that indicates that the following four types are supported: EAP_AKA, EAP_SIM, EAP_TLS, and EAP_TTLS."
			::= { hwNAIRealmProfileEntry 3 }

		 --1.3.6.1.4.1.2011.6.139.11.1.51.1.4
		hwNAIRealmEapAuthenID OBJECT-TYPE
			SYNTAX Unsigned32 (0..255 | 4294967295)
			MAX-ACCESS not-accessible
			STATUS current
			DESCRIPTION 
				"This object indicates the authorization ID.
The default value is 0xffffffff that indicates that all IDs within the value range are supported."
			::= { hwNAIRealmProfileEntry 4 }

		 --1.3.6.1.4.1.2011.6.139.11.1.51.1.5
		hwNAIRealmEapAuthenPara OBJECT-TYPE
			SYNTAX Unsigned32 (0..255 | 4294967295)
			MAX-ACCESS read-write
			STATUS current
			DESCRIPTION 
				"This object indicate authorization parameter.
The default value is 0xffffffff that indicates all parameters within the value range are supported."
			::= { hwNAIRealmProfileEntry 5 }

		 --1.3.6.1.4.1.2011.6.139.11.1.51.1.6
		hwNAIRealmProfileRowStatus OBJECT-TYPE
			SYNTAX RowStatus
			MAX-ACCESS read-write
			STATUS current
			DESCRIPTION 
				"This object indicates the row status of this table. createAndGo(4) and destroy(6) are commonly used."
			::= { hwNAIRealmProfileEntry 6 }

		--1.3.6.1.4.1.2011.6.139.11.1.52
		hwVenueNameProfileTable OBJECT-TYPE
			SYNTAX SEQUENCE OF HwVenueNameProfileEntry 
			MAX-ACCESS not-accessible
			STATUS current
			DESCRIPTION 
				"This table is used to configure and query venue name profile parameters."
			::= { hwWlanConfigObjects 52 }

		--1.3.6.1.4.1.2011.6.139.11.1.52.1
		hwVenueNameProfileEntry OBJECT-TYPE
			SYNTAX HwVenueNameProfileEntry 
			MAX-ACCESS not-accessible
			STATUS current
			DESCRIPTION 
				"The index of this table is hwVenueNameProfileName."
			INDEX { hwVenueNameProfileName }
			::= { hwVenueNameProfileTable 1 }


		HwVenueNameProfileEntry ::=
			SEQUENCE {				
				hwVenueNameProfileName
					OCTET STRING,
				hwVenueNameLanguageCodeList
					OCTET STRING,
				hwVenueNameList
					OCTET STRING,
				hwVenueNameProfileRowStatus
					RowStatus 
			 }

		 --1.3.6.1.4.1.2011.6.139.11.1.52.1.1
		hwVenueNameProfileName OBJECT-TYPE
			SYNTAX OCTET STRING (SIZE (1..35))
			MAX-ACCESS not-accessible
			STATUS current
			DESCRIPTION 
				"This object indicates the name of a venue name profile. It is the index of the table."
			::= { hwVenueNameProfileEntry 1 }

		 --1.3.6.1.4.1.2011.6.139.11.1.52.1.2
		hwVenueNameLanguageCodeList OBJECT-TYPE
			SYNTAX OCTET STRING (SIZE (0..256))
			MAX-ACCESS read-write
			STATUS current
			DESCRIPTION 
				"A value of LanguageCode indicates a language. It is a string of 2-3 characters.
For details about GUI value ranges, see ISO 639 on the Codes for the Representation of Names of Languages page. The path is http://www.loc.gov/standards/iso639-2/php/ code_list.php. chi/zho/zh indicates Chinese and eng/en indicates English.
NOTE By default, no configuration is added.Values of LanguageCode are separated by question marks (?).A maximum of 32 LanguageCode values can be configured.A LanguageCode value must match a VenueName value."
			::= { hwVenueNameProfileEntry 2 }

		 --1.3.6.1.4.1.2011.6.139.11.1.52.1.3
		hwVenueNameList OBJECT-TYPE
			SYNTAX OCTET STRING (SIZE (0..2048))
			MAX-ACCESS read-write
			STATUS current
			DESCRIPTION 
				"If the language-code is set to eng, the name is a string of characters. Rules are the same as those for SSIDs. When it is set to other values, the venue-name is set to a hexadecimal UTF-8 code because current WLANs support English only, for example, venue-name language-code ZHO name 025AB1472568.
NOTE By default, no configuration is added.A venue-name value cannot exceed 32 characters.venue-name values are separated by question marks (?).A LanguageCode value must match a VenueName value."
			::= { hwVenueNameProfileEntry 3 }

		 --1.3.6.1.4.1.2011.6.139.11.1.52.1.4
		hwVenueNameProfileRowStatus OBJECT-TYPE
			SYNTAX RowStatus
			MAX-ACCESS read-write
			STATUS current
			DESCRIPTION 
				"This object indicates the row status of this table. createAndGo(4) and destroy(6) are commonly used."
			::= { hwVenueNameProfileEntry 4 }

		--1.3.6.1.4.1.2011.6.139.11.1.53
		hwRoamingConsortiumProfileTable OBJECT-TYPE
			SYNTAX SEQUENCE OF HwRoamingConsortiumProfileEntry 
			MAX-ACCESS not-accessible
			STATUS current
			DESCRIPTION 
				"This table is used to configure and query roaming consortium profile parameters."
			::= { hwWlanConfigObjects 53 }

		--1.3.6.1.4.1.2011.6.139.11.1.53.1
		hwRoamingConsortiumProfileEntry OBJECT-TYPE
			SYNTAX HwRoamingConsortiumProfileEntry 
			MAX-ACCESS not-accessible
			STATUS current
			DESCRIPTION 
				"The index of this table is hwRoamingConsortiumProfileName."
			INDEX { hwRoamingConsortiumProfileName }
			::= { hwRoamingConsortiumProfileTable 1 }


		HwRoamingConsortiumProfileEntry ::=
			SEQUENCE {				
				hwRoamingConsortiumProfileName
					OCTET STRING,
				hwRoamingConsortiumOIList
					OCTET STRING,
				hwRoamingConsortiumOIInBeaconList
					OCTET STRING,
				hwRoamingConsortiumProfileRowStatus
					RowStatus 
			 }

		 --1.3.6.1.4.1.2011.6.139.11.1.53.1.1
		hwRoamingConsortiumProfileName OBJECT-TYPE
			SYNTAX OCTET STRING (SIZE (1..35))
			MAX-ACCESS not-accessible
			STATUS current
			DESCRIPTION 
				"This object indicates the name of a roaming consortium profile. It is the index of the table."
			::= { hwRoamingConsortiumProfileEntry 1 }

		 --1.3.6.1.4.1.2011.6.139.11.1.53.1.2
		hwRoamingConsortiumOIList OBJECT-TYPE
			SYNTAX OCTET STRING
			MAX-ACCESS read-write
			STATUS current
			DESCRIPTION 
				"This object indicates the roaming consortium member.
The roaming consortium OI is a hexadecimal number in the format of HH-HH-HH or HH-HH-HH-HH-HH. The length of a roaming consortium OI is three to five bytes, for example, 12-34-56?12-34-58?34-45-67.
NOTE By default, no configuration is added.RoamingConsortiumOI values are separated by question marks (?).A maximum of 32 RoamingConsortiumOI values can be configured.A RoamingConsortiumOI value must match an OIInBeacon value."
			::= { hwRoamingConsortiumProfileEntry 2 }

		 --1.3.6.1.4.1.2011.6.139.11.1.53.1.3
		hwRoamingConsortiumOIInBeaconList OBJECT-TYPE
			SYNTAX OCTET STRING
			MAX-ACCESS read-write
			STATUS current
			DESCRIPTION 
				"This object indicates whether a roaming consortium member carries the inbeacon tag, for example, YES?NO?NO.
NOTE By default, no configuration is added.A RoamingConsortiumOI value must match an OIInBeacon value.A maximum of three RoamingConsortiumOI values can be configured.in-beacon can be set to YES."
			::= { hwRoamingConsortiumProfileEntry 3 }

		 --1.3.6.1.4.1.2011.6.139.11.1.53.1.4
		hwRoamingConsortiumProfileRowStatus OBJECT-TYPE
			SYNTAX RowStatus
			MAX-ACCESS read-write
			STATUS current
			DESCRIPTION 
				"This object indicates the row status of this table. createAndGo(4) and destroy(6) are commonly used."
			::= { hwRoamingConsortiumProfileEntry 4 }
		

		-- 1.3.6.1.4.1.2011.6.139.11.1.54
		hwSACProfileTable OBJECT-TYPE
			SYNTAX SEQUENCE OF HwSACProfileEntry 
			MAX-ACCESS not-accessible
			STATUS current
			DESCRIPTION 
				"This table is used to configure and query SAC profile parameters."
			::= { hwWlanConfigObjects 54 }
		

		-- 1.3.6.1.4.1.2011.6.139.11.1.54.1
		hwSACProfileEntry OBJECT-TYPE
			SYNTAX HwSACProfileEntry 
			MAX-ACCESS not-accessible
			STATUS current
			DESCRIPTION 
				"The index of this table is hwSACProfileName."
			INDEX { hwSACProfileName }
			::= { hwSACProfileTable 1 }


		HwSACProfileEntry ::=
			SEQUENCE {				
				hwSACProfileName
					OCTET STRING,
				hwSACProfUserStat
					INTEGER,
				hwSACProfVapStat
					INTEGER,
				hwSACProfRowStatus
					RowStatus 
			 }

	
		-- 1.3.6.1.4.1.2011.6.139.11.1.54.1.1
		hwSACProfileName OBJECT-TYPE
			SYNTAX OCTET STRING (SIZE (1..35))
			MAX-ACCESS not-accessible
			STATUS current
			DESCRIPTION 
				"This object indicates the name of an SAC profile. It is the index of the table."
			::= { hwSACProfileEntry 1 }

	
		-- 1.3.6.1.4.1.2011.6.139.11.1.54.1.2
		hwSACProfUserStat OBJECT-TYPE
			SYNTAX INTEGER
				{
				disable(1),
				enable(2)
				}
			MAX-ACCESS read-write
			STATUS current
			DESCRIPTION 
				"This object indicates whether the user statistics function is enabled in the SAC profile.
The default value is disable (1)."
			::= { hwSACProfileEntry 2 }

		 
		-- 1.3.6.1.4.1.2011.6.139.11.1.54.1.3
		hwSACProfVapStat OBJECT-TYPE
			SYNTAX INTEGER
				{
				disable(1),
				enable(2)
				}
			MAX-ACCESS read-write
			STATUS current
			DESCRIPTION 
				"This object indicates whether the VAP statistics function is enabled in the SAC profile.
The default value is disable (1)."
			::= { hwSACProfileEntry 3 }


		-- 1.3.6.1.4.1.2011.6.139.11.1.54.1.4
		hwSACProfRowStatus OBJECT-TYPE
			SYNTAX RowStatus
			MAX-ACCESS read-write
			STATUS current
			DESCRIPTION 
				"This object indicates the row status."
			::= { hwSACProfileEntry 4 }

		-- 1.3.6.1.4.1.2011.6.139.11.1.55
		hwSACProfileActionTable OBJECT-TYPE
			SYNTAX SEQUENCE OF HwSACProfileActionEntry 
			MAX-ACCESS not-accessible
			STATUS current
			DESCRIPTION 
				"This table describes SAC profile action configurations.This table is used to configure actions in an SAC profile."
			::= { hwWlanConfigObjects 55 }
		
		-- 1.3.6.1.4.1.2011.6.139.11.1.55.1
		hwSACProfileActionEntry OBJECT-TYPE
			SYNTAX HwSACProfileActionEntry 
			MAX-ACCESS not-accessible
			STATUS current
			DESCRIPTION 
				"Indexes of this table are hwSACProfileName and hwSACProfileActionIndex."
			INDEX { hwSACProfileName,hwSACProfileActionIndex}
			::= { hwSACProfileActionTable 1 }


		HwSACProfileActionEntry ::=
			SEQUENCE {				
				hwSACProfileActionIndex
					Unsigned32,
				hwSACProfileActProtocolType
					INTEGER,
				hwSACProfileActProtocolName
					OCTET STRING,
				hwSACProfileActProtocolGrpName
					OCTET STRING,
				hwSACProfileActionType
					INTEGER,
				hwSACProfileActCarCir
					Unsigned32,
				hwSACProfileActRemarkDscpValue
					Unsigned32,
				hwSACProfileActRemark8021pValue
					Unsigned32,
				hwSACProfileActionRowstatus
					RowStatus 
			 }

		-- 1.3.6.1.4.1.2011.6.139.11.1.55.1.1
		hwSACProfileActionIndex OBJECT-TYPE
			SYNTAX Unsigned32
			MAX-ACCESS not-accessible
			STATUS current
			DESCRIPTION 
				"This object indicates the internal index of the action. It is the index of the table."
			::= { hwSACProfileActionEntry 1 }

		-- 1.3.6.1.4.1.2011.6.139.11.1.55.1.2
		hwSACProfileActProtocolType OBJECT-TYPE
			SYNTAX INTEGER
				{
				unknown(0) ,
				application(1) ,
				applicationGroup(2)
				}
			MAX-ACCESS read-write
			STATUS current
			DESCRIPTION 
				"This object indicates the protocol type."
			::= { hwSACProfileActionEntry 2 }

		-- 1.3.6.1.4.1.2011.6.139.11.1.55.1.3
		hwSACProfileActProtocolName OBJECT-TYPE
			SYNTAX OCTET STRING (SIZE (0..255))
			MAX-ACCESS read-write
			STATUS current
			DESCRIPTION 
				"This object indicates the protocol name."
			::= { hwSACProfileActionEntry 3 }

		-- 1.3.6.1.4.1.2011.6.139.11.1.55.1.4
		hwSACProfileActProtocolGrpName OBJECT-TYPE
			SYNTAX OCTET STRING (SIZE (0..35))
			MAX-ACCESS read-write
			STATUS current
			DESCRIPTION 
				"This object indicates the protocol group name."
			::= { hwSACProfileActionEntry 4 }
		

		-- 1.3.6.1.4.1.2011.6.139.11.1.55.1.5
		hwSACProfileActionType OBJECT-TYPE
			SYNTAX INTEGER
				{
				unknown(0) ,
				deny(1),
				car(2),
				remarkDscp(3),
				remark8021p(4),
				dynamicOptimization(5),
				voiceDynamicOptimization(6),
				videoDynamicOptimization(7)
				}
			MAX-ACCESS read-create
			STATUS current
			DESCRIPTION 
				"This object indicates the action type."
			::= { hwSACProfileActionEntry 5 }
		

		-- 1.3.6.1.4.1.2011.6.139.11.1.55.1.6
		hwSACProfileActCarCir OBJECT-TYPE
			SYNTAX Unsigned32 (64..10000000|4294967295)
			MAX-ACCESS read-write
			STATUS current
			DESCRIPTION 
				"This object indicates the CAR CIR value."
			::= { hwSACProfileActionEntry 6 }
		

		-- 1.3.6.1.4.1.2011.6.139.11.1.55.1.7
		hwSACProfileActRemarkDscpValue OBJECT-TYPE
			SYNTAX Unsigned32 (0..63)
			MAX-ACCESS read-write
			STATUS current
			DESCRIPTION 
				"This object indicates the DSCP value."
			::= { hwSACProfileActionEntry 7 }
		

		-- 1.3.6.1.4.1.2011.6.139.11.1.55.1.8
		hwSACProfileActRemark8021pValue OBJECT-TYPE
			SYNTAX Unsigned32 (0..7)
			MAX-ACCESS read-write
			STATUS current
			DESCRIPTION 
				"This object indicates the 802.1p priority."
			::= { hwSACProfileActionEntry 8 }
		

		-- 1.3.6.1.4.1.2011.6.139.11.1.55.1.9
		hwSACProfileActionRowstatus OBJECT-TYPE
			SYNTAX RowStatus
			MAX-ACCESS read-write
			STATUS current
			DESCRIPTION 
				"This object indicates the row status."
			::= { hwSACProfileActionEntry 9 }
		

		-- 1.3.6.1.4.1.2011.6.139.11.1.56
		hwWlanAPProvision OBJECT IDENTIFIER ::= { hwWlanConfigObjects 56 }

		

		 --1.3.6.1.4.1.2011.6.139.11.1.59.2
		-- 1.3.6.1.4.1.2011.6.139.11.1.56.1
		hwWlanAPProvisionAddressMode OBJECT-TYPE
			SYNTAX INTEGER
				{
				static(1),
				dhcp(2),
				slaac(3),
				invalid(-1)
				}
			MAX-ACCESS read-write
			STATUS current
			DESCRIPTION 
				"This object indicates the IPv4 address allocation mode."
			::= { hwWlanAPProvision 1 }

		 --1.3.6.1.4.1.2011.6.139.11.1.59.3
		hwWlanAPProvisionIPv4Address OBJECT-TYPE
			SYNTAX IpAddress
			MAX-ACCESS read-write
			STATUS current
			DESCRIPTION 
				"This object indicates the AP's IPv4 address.
hwWlanAPProvisionIPv4Address takes effect if hwAPIPv4Method is set to static."
			::= { hwWlanAPProvision 2 }

		 --1.3.6.1.4.1.2011.6.139.11.1.59.4
		hwWlanAPProvisionIPv4Mask OBJECT-TYPE
			SYNTAX IpAddress
			MAX-ACCESS read-write
			STATUS current
			DESCRIPTION 
				"This object indicates the AP's IPv4 mask.
hwWlanAPProvisionIPv4Mask takes effect if hwAPIPv4Method is set to static."
			::= { hwWlanAPProvision 3 }

		 --1.3.6.1.4.1.2011.6.139.11.1.59.5
		hwWlanAPProvisionIPv4Gateway OBJECT-TYPE
			SYNTAX IpAddress
			MAX-ACCESS read-write
			STATUS current
			DESCRIPTION 
				"This object indicates the AP's IPv4 gateway.
hwWlanAPProvisionIPv4Gateway takes effect if hwAPIPv4Method is set to static."
			::= { hwWlanAPProvision 4 }

		 --1.3.6.1.4.1.2011.6.139.11.1.59.6
		hwWlanAPProvisionIPv6Address OBJECT-TYPE
			SYNTAX OCTET STRING (SIZE (0..46))
			MAX-ACCESS read-write
			STATUS current
			DESCRIPTION 
				"This object indicates the AP's IPv6 address.
hwWlanAPProvisionIPv6Address takes effect if hwAPIPv6Method is set to static."
			::= { hwWlanAPProvision 5 }

		 --1.3.6.1.4.1.2011.6.139.11.1.59.7
		hwWlanAPProvisionIPv6PrefixLen OBJECT-TYPE
			SYNTAX Unsigned32 (0..128)
			MAX-ACCESS read-write
			STATUS current
			DESCRIPTION 
				"This object indicates the length of the IPv6 address prefix."
			::= { hwWlanAPProvision 6 }

		
		 --1.3.6.1.4.1.2011.6.139.11.1.59.8
		hwWlanAPProvisionIPv6Gateway OBJECT-TYPE
			SYNTAX OCTET STRING (SIZE (0..46))
			MAX-ACCESS read-write
			STATUS current
			DESCRIPTION 
				"This object indicates the AP's IPv6 gateway.
hwWlanAPProvisionIPv6Gateway takes effect if hwAPIPv6Method is set to static."
			::= { hwWlanAPProvision 7 }

		 --1.3.6.1.4.1.2011.6.139.11.1.59.9
		hwWlanAPProvisionGroupName OBJECT-TYPE
			SYNTAX OCTET STRING (SIZE (0..35))
			MAX-ACCESS read-write
			STATUS current
			DESCRIPTION 
				"This object indicates the group name."
			::= { hwWlanAPProvision 8 }

		 --1.3.6.1.4.1.2011.6.139.11.1.59.10
		hwWlanAPProvisionName OBJECT-TYPE
			SYNTAX OCTET STRING (SIZE (0..31))
			MAX-ACCESS read-write
			STATUS current
			DESCRIPTION 
				"This object indicates the name of an AP."
			::= { hwWlanAPProvision 9 }

		 --1.3.6.1.4.1.2011.6.139.11.1.59.11
		hwWlanAPProvisionIPv4ACList OBJECT-TYPE
			SYNTAX OCTET STRING
			MAX-ACCESS read-write
			STATUS current
			DESCRIPTION 
				"This object indicates the AC IPv4 address list.
NOTE ACL rules are separated by question marks (?).A maximum of four ACL rules can be configured."
			::= { hwWlanAPProvision 10 }

		 --1.3.6.1.4.1.2011.6.139.11.1.59.12
		hwWlanAPProvisionIPv6ACList OBJECT-TYPE
			SYNTAX OCTET STRING
			MAX-ACCESS read-write
			STATUS current
			DESCRIPTION 
				"This object indicates the AC IPv6 address list.
NOTE ACL rules are separated by question marks (?).A maximum of four ACL rules can be configured."
			::= { hwWlanAPProvision 11 }

		 --1.3.6.1.4.1.2011.6.139.11.1.59.13
		hwWlanAPProvisionCommitAPName OBJECT-TYPE
			SYNTAX OCTET STRING (SIZE (1..31))
			MAX-ACCESS read-write
			STATUS current
			DESCRIPTION 
				"This object indicates that the configuration is delivered based on AP names."
			::= { hwWlanAPProvision 12 }

		 --1.3.6.1.4.1.2011.6.139.11.1.59.14
		hwWlanAPProvisionCommitAPMac OBJECT-TYPE
			SYNTAX MacAddress
			MAX-ACCESS read-write
			STATUS current
			DESCRIPTION 
				"This object indicates that the configuration is delivered based on MAC addresses of APs."
			::= { hwWlanAPProvision 13 }

		 --1.3.6.1.4.1.2011.6.139.11.1.59.15
		hwWlanAPProvisionCommitAPGroup OBJECT-TYPE
			SYNTAX OCTET STRING (SIZE (1..35))
			MAX-ACCESS read-write
			STATUS current
			DESCRIPTION 
				"This object indicates that the configuration is delivered based on AP groups."
			::= { hwWlanAPProvision 14 }

		--1.3.6.1.4.1.2011.6.139.11.1.60
		hwWlanRadioCalibrateManagement OBJECT IDENTIFIER ::= { hwWlanConfigObjects 57 }

	
		-- 1.3.6.1.4.1.2011.6.139.11.1.57.1
		hwWlanRadioCalibrateMode OBJECT-TYPE
			SYNTAX INTEGER
				{
				auto(1),
				manual(2),
				schedule(3)
				}
			MAX-ACCESS read-write
			STATUS current
			DESCRIPTION 
				"This object indicates the radio calibration mode.
The default value is auto(1)."
			::= { hwWlanRadioCalibrateManagement 1 }

		-- 1.3.6.1.4.1.2011.6.139.11.1.57.2
		hwWlanRadioCalibrateScheduleTime OBJECT-TYPE
			SYNTAX OCTET STRING
			MAX-ACCESS read-write
			STATUS current
			DESCRIPTION 
				"This object indicates the scheduled radio calibration time."
			::= { hwWlanRadioCalibrateManagement 2 }

	
		-- 1.3.6.1.4.1.2011.6.139.11.1.57.3
		hwWlanRadioCalibrateManualStartup OBJECT-TYPE
			SYNTAX Integer32 (1)
			MAX-ACCESS read-write
			STATUS current
			DESCRIPTION 
				"This object indicates the manually triggered radio calibration. It is valid only when the radio calibration mode is manual."
			::= { hwWlanRadioCalibrateManagement 3 }

		 
		-- 1.3.6.1.4.1.2011.6.139.11.1.57.4
		hwWlanRadioCalibrateAutoInterval OBJECT-TYPE
			SYNTAX Integer32 (30..1440)
			MAX-ACCESS read-write
			STATUS current
			DESCRIPTION 
				"This object indicates the automatic radio calibration interval.
It is expressed in minutes.
The default value is 1440."
			::= { hwWlanRadioCalibrateManagement 4 }


		-- 1.3.6.1.4.1.2011.6.139.11.1.57.5
		hwWlanRadioCalibratePolicy OBJECT-TYPE
			SYNTAX Unsigned32
			MAX-ACCESS read-write
			STATUS current
			DESCRIPTION 
				"This object indicates the radio calibration policy.bit0: rogue-ap bit1: nonWifi bit2: load
The default value is 0, indicating that this function is not enabled."
			::= { hwWlanRadioCalibrateManagement 5 }

		 --1.3.6.1.4.1.2011.6.139.11.1.60.6
		-- 1.3.6.1.4.1.2011.6.139.11.1.57.6
		hwWlanRadioCalibrateSensitivity OBJECT-TYPE
			SYNTAX INTEGER
				{
				medium(1),
				high(2),
				low(3)
				}
			MAX-ACCESS read-write
			STATUS current
			DESCRIPTION 
				"This object indicates the radio calibration sensitivity.
The default value is medium(2)."
			::= { hwWlanRadioCalibrateManagement 6 }

		 --1.3.6.1.4.1.2011.6.139.11.1.60.7
		-- 1.3.6.1.4.1.2011.6.139.11.1.57.7
		hwWlanRadioCalibrateAutoStartTime OBJECT-TYPE
			SYNTAX OCTET STRING
			MAX-ACCESS read-write
			STATUS current
			DESCRIPTION 
				"This object indicates the start time of automatic radio calibration.
The default value is 00:00:00."
			::= { hwWlanRadioCalibrateManagement 7 }

		--1.3.6.1.4.1.2011.6.139.11.1.61
		-- 1.3.6.1.4.1.2011.6.139.11.1.58
		hwWlanMobilityObjects OBJECT IDENTIFIER ::= { hwWlanConfigObjects 58 }
		
--  1.3.6.1.4.1.2011.6.139.11.1.61.1
-- 1.3.6.1.4.1.2011.6.139.11.1.61.1
		-- 1.3.6.1.4.1.2011.6.139.11.1.58.1
		hwWlanMobilityManagement OBJECT IDENTIFIER ::= { hwWlanMobilityObjects 1 }

		 --1.3.6.1.4.1.2011.6.139.11.1.61.1.1
		-- 1.3.6.1.4.1.2011.6.139.11.1.58.1.1
		hwWlanMasterControllerSwitch OBJECT-TYPE
			SYNTAX INTEGER
				{
				disable(1) ,
				enable(2)
				}
			MAX-ACCESS read-write
			STATUS current
			DESCRIPTION 
				"This object indicates the status of the CUC function.
The default value is disable (1)."
			::= { hwWlanMobilityManagement 1 }

		 --1.3.6.1.4.1.2011.6.139.11.1.61.1.2
		-- 1.3.6.1.4.1.2011.6.139.11.1.58.1.2
		hwWlanConnectMasterControllerSwitch OBJECT-TYPE
			SYNTAX INTEGER
				{
				disconnect(1) ,
				connect(2)
				}
			MAX-ACCESS read-write
			STATUS current
			DESCRIPTION 
				"This objection indicates the status of the connection between the AC and Master Controller. The establishment of connection between the AC and Master Controller requires the IP address of the Master Controller.
The default value is disconnect(1)."
			::= { hwWlanMobilityManagement 2 }

		 --1.3.6.1.4.1.2011.6.139.11.1.61.1.3
		-- 1.3.6.1.4.1.2011.6.139.11.1.58.1.3
		hwWlanConnectMasterControllerIPv4Addr OBJECT-TYPE
			SYNTAX IpAddress
			MAX-ACCESS read-write
			STATUS current
			DESCRIPTION 
				"This object indicates the IPv4 address of the CUC that needs to set up a link with the Master Controller."
			::= { hwWlanMobilityManagement 3 }

		 --1.3.6.1.4.1.2011.6.139.11.1.61.1.4
		-- 1.3.6.1.4.1.2011.6.139.11.1.58.1.4
		hwWlanConnectMasterControllerIPv6Addr OBJECT-TYPE
			SYNTAX OCTET STRING
			MAX-ACCESS read-write
			STATUS current
			DESCRIPTION 
				"This object indicates the IPv6 address of the CUC that needs to set up a link with the Master Controller."
			::= { hwWlanMobilityManagement 4 }

		--1.3.6.1.4.1.2011.6.139.11.1.61.2
		-- 1.3.6.1.4.1.2011.6.139.11.1.58.2
		hwWlanMobilityAcTable OBJECT-TYPE
			SYNTAX SEQUENCE OF HwWlanMobilityAcEntry 
			MAX-ACCESS not-accessible
			STATUS current
			DESCRIPTION 
				"Description."
			::= { hwWlanMobilityObjects 2 }

		--1.3.6.1.4.1.2011.6.139.11.1.61.2.1
		-- 1.3.6.1.4.1.2011.6.139.11.1.58.2.1
		hwWlanMobilityAcEntry OBJECT-TYPE
			SYNTAX HwWlanMobilityAcEntry 
			MAX-ACCESS not-accessible
			STATUS current
			DESCRIPTION 
				"The index of this table is hwWlanMemAcIndex."
			INDEX { hwWlanMemAcIndex }
			::= { hwWlanMobilityAcTable 1 }


		HwWlanMobilityAcEntry ::=
			SEQUENCE {				
				hwWlanMemAcIndex
					Integer32,
				hwWlanAcIPv4Address
					IpAddress,
				hwWlanAcIPv6Address
					OCTET STRING,
				hwWlanAcState
					INTEGER,
				hwWlanAcRowStatus
					RowStatus 
			 }

		 --1.3.6.1.4.1.2011.6.139.11.1.61.2.1.1
		-- 1.3.6.1.4.1.2011.6.139.11.1.58.2.1.1
		hwWlanMemAcIndex OBJECT-TYPE
			SYNTAX Integer32
			MAX-ACCESS not-accessible
			STATUS current
			DESCRIPTION 
				"This object indicates the AP ID."
			::= { hwWlanMobilityAcEntry 1 }

		 --1.3.6.1.4.1.2011.6.139.11.1.61.2.1.2
		-- 1.3.6.1.4.1.2011.6.139.11.1.58.2.1.2
		hwWlanAcIPv4Address OBJECT-TYPE
			SYNTAX IpAddress
			MAX-ACCESS read-write
			STATUS current
			DESCRIPTION 
				"This object indicates the AC's IPv4 address."
			::= { hwWlanMobilityAcEntry 2 }

		 --1.3.6.1.4.1.2011.6.139.11.1.61.2.1.3
		-- 1.3.6.1.4.1.2011.6.139.11.1.58.2.1.3
		hwWlanAcIPv6Address OBJECT-TYPE
			SYNTAX OCTET STRING
			MAX-ACCESS read-write
			STATUS current
			DESCRIPTION 
				"This object indicates the AC's IPv6 address."
			::= { hwWlanMobilityAcEntry 3 }

		 --1.3.6.1.4.1.2011.6.139.11.1.61.2.1.4
		-- 1.3.6.1.4.1.2011.6.139.11.1.58.2.1.4
		hwWlanAcState OBJECT-TYPE
			SYNTAX INTEGER
				{
				normal(1) ,
				fault(2)
				}
			MAX-ACCESS read-only
			STATUS current
			DESCRIPTION 
				"This object indicates the state of connections to the AC."
			::= { hwWlanMobilityAcEntry 4 }

		 --1.3.6.1.4.1.2011.6.139.11.1.61.2.1.5
		-- 1.3.6.1.4.1.2011.6.139.11.1.58.2.1.5
		hwWlanAcRowStatus OBJECT-TYPE
			SYNTAX RowStatus
			MAX-ACCESS read-write
			STATUS current
			DESCRIPTION 
				"This object indicates the row status."
			::= { hwWlanMobilityAcEntry 5 }

		--1.3.6.1.4.1.2011.6.139.11.1.61.3
		-- 1.3.6.1.4.1.2011.6.139.11.1.58.3
		hwWlanMobilityGroupTable OBJECT-TYPE
			SYNTAX SEQUENCE OF HwWlanMobilityGroupEntry 
			MAX-ACCESS not-accessible
			STATUS current
			DESCRIPTION 
				"Description."
			::= { hwWlanMobilityObjects 3 }

		--1.3.6.1.4.1.2011.6.139.11.1.61.3.1
		-- 1.3.6.1.4.1.2011.6.139.11.1.58.3.1
		hwWlanMobilityGroupEntry OBJECT-TYPE
			SYNTAX HwWlanMobilityGroupEntry 
			MAX-ACCESS not-accessible
			STATUS current
			DESCRIPTION 
				"The index of this table is hwWlanMobilityGroupName."
			INDEX { hwWlanMobilityGroupName }
			::= { hwWlanMobilityGroupTable 1 }


		HwWlanMobilityGroupEntry ::=
			SEQUENCE {				
				hwWlanMobilityGroupName
					OCTET STRING,
				hwWlanMobilityGroupRowStatus
					RowStatus 
			 }

		 --1.3.6.1.4.1.2011.6.139.11.1.61.3.1.1
		-- 1.3.6.1.4.1.2011.6.139.11.1.58.3.1.1
		hwWlanMobilityGroupName OBJECT-TYPE
			SYNTAX OCTET STRING
			MAX-ACCESS not-accessible
			STATUS current
			DESCRIPTION 
				"This object indicates the mobility group name."
			::= { hwWlanMobilityGroupEntry 1 }

		 --1.3.6.1.4.1.2011.6.139.11.1.61.3.1.2
		-- 1.3.6.1.4.1.2011.6.139.11.1.58.3.1.2
		hwWlanMobilityGroupRowStatus OBJECT-TYPE
			SYNTAX RowStatus
			MAX-ACCESS read-write
			STATUS current
			DESCRIPTION 
				"This object indicates to add or delete mobility groups."
			::= { hwWlanMobilityGroupEntry 2 }

		--1.3.6.1.4.1.2011.6.139.11.1.61.4
		-- 1.3.6.1.4.1.2011.6.139.11.1.58.4
		hwWlanMobilityGroupMemberTable OBJECT-TYPE
			SYNTAX SEQUENCE OF HwWlanMobilityGroupMemberEntry 
			MAX-ACCESS not-accessible
			STATUS current
			DESCRIPTION 
				"Description."
			::= { hwWlanMobilityObjects 4 }

		--1.3.6.1.4.1.2011.6.139.11.1.61.4.1
		-- 1.3.6.1.4.1.2011.6.139.11.1.58.4.1
		hwWlanMobilityGroupMemberEntry OBJECT-TYPE
			SYNTAX HwWlanMobilityGroupMemberEntry 
			MAX-ACCESS not-accessible
			STATUS current
			DESCRIPTION 
				"Indexes of this table are hwWlanMobilityGroupName and hwWlanMobilityGroupMemberACIndex."
			INDEX { hwWlanMobilityGroupMemberACIndex,hwWlanMobilityGroupName }
			::= { hwWlanMobilityGroupMemberTable 1 }


		HwWlanMobilityGroupMemberEntry ::=
			SEQUENCE {				
				hwWlanMobilityGroupMemberACIndex
					Integer32,
				hwWlanMobilityGroupMemberRowStatus
					RowStatus 
			 }

		 --1.3.6.1.4.1.2011.6.139.11.1.61.4.1.1
		-- 1.3.6.1.4.1.2011.6.139.11.1.58.4.1.1
		hwWlanMobilityGroupMemberACIndex OBJECT-TYPE
			SYNTAX Integer32
			MAX-ACCESS not-accessible
			STATUS current
			DESCRIPTION 
				"This object indicates mobility group members (AC ID)."
			::= { hwWlanMobilityGroupMemberEntry 1 }

		 --1.3.6.1.4.1.2011.6.139.11.1.61.4.1.2
		-- 1.3.6.1.4.1.2011.6.139.11.1.58.4.1.2
		hwWlanMobilityGroupMemberRowStatus OBJECT-TYPE
			SYNTAX RowStatus
			MAX-ACCESS read-write
			STATUS current
			DESCRIPTION 
				"This object indicates to add or delete mobility group members."
			::= { hwWlanMobilityGroupMemberEntry 2 }

		--1.3.6.1.4.1.2011.6.139.11.1.62
		-- 1.3.6.1.4.1.2011.6.139.11.1.59
		hwWlanLanguageCodeTable OBJECT-TYPE
			SYNTAX SEQUENCE OF HwWlanLanguageCodeEntry 
			MAX-ACCESS not-accessible
			STATUS current
			DESCRIPTION 
				"It is the language code table. It complies with ISO 639 and is used by hotspot networks to obtain language code information."
			::= { hwWlanConfigObjects 59 }
		
--  1.3.6.1.4.1.2011.6.139.11.1.62.1
-- 1.3.6.1.4.1.2011.6.139.11.1.62.1
		-- 1.3.6.1.4.1.2011.6.139.11.1.59.1
		hwWlanLanguageCodeEntry OBJECT-TYPE
			SYNTAX HwWlanLanguageCodeEntry 
			MAX-ACCESS not-accessible
			STATUS current
			DESCRIPTION 
				"The index of this table is hwWlanLanguageCode."
			INDEX { hwWlanLanguageCode }
			::= { hwWlanLanguageCodeTable 1 }


		HwWlanLanguageCodeEntry ::=
			SEQUENCE {				
				hwWlanLanguageCode
					OCTET STRING,
				hwWlanLanguageCodeDescription
					OCTET STRING 
			 }

		 --1.3.6.1.4.1.2011.6.139.11.1.62.1.1
		-- 1.3.6.1.4.1.2011.6.139.11.1.59.1.1
		hwWlanLanguageCode OBJECT-TYPE
			SYNTAX OCTET STRING (SIZE (2..3))
			MAX-ACCESS not-accessible
			STATUS current
			DESCRIPTION 
				"This object indicates the language code."
			::= { hwWlanLanguageCodeEntry 1 }

		 --1.3.6.1.4.1.2011.6.139.11.1.62.1.2
		-- 1.3.6.1.4.1.2011.6.139.11.1.59.1.2
		hwWlanLanguageCodeDescription OBJECT-TYPE
			SYNTAX OCTET STRING
			MAX-ACCESS read-only
			STATUS current
			DESCRIPTION 
				"This object indicates the description of language codes."
			::= { hwWlanLanguageCodeEntry 2 }

		--1.3.6.1.4.1.2011.6.139.11.1.63
		-- 1.3.6.1.4.1.2011.6.139.11.1.60
		hwFatApConfigObjects OBJECT IDENTIFIER ::= { hwWlanConfigObjects 60 }
		
--  1.3.6.1.4.1.2011.6.139.11.1.63.1
-- 1.3.6.1.4.1.2011.6.139.11.1.63.1
		-- 1.3.6.1.4.1.2011.6.139.11.1.60.1
		hwFatApGlobalConfig OBJECT IDENTIFIER ::= { hwFatApConfigObjects 1 }

		 --1.3.6.1.4.1.2011.6.139.11.1.63.1.1
		-- 1.3.6.1.4.1.2011.6.139.11.1.60.1.1
		hwFatApCountryCode OBJECT-TYPE
			SYNTAX OCTET STRING (SIZE (2..8))
			MAX-ACCESS read-write
			STATUS current
			DESCRIPTION 
				"Description."
			::= { hwFatApGlobalConfig 1 }

		 --1.3.6.1.4.1.2011.6.139.11.1.63.1.2
		-- 1.3.6.1.4.1.2011.6.139.11.1.60.1.2
		hwFatApMaxStaNum OBJECT-TYPE
			SYNTAX Unsigned32 (1..256)
			MAX-ACCESS read-write
			STATUS current
			DESCRIPTION 
				"Description."
			::= { hwFatApGlobalConfig 2 }

		 --1.3.6.1.4.1.2011.6.139.11.1.63.1.3
		-- 1.3.6.1.4.1.2011.6.139.11.1.60.1.3
		hwFatApStaAccessMode OBJECT-TYPE
			SYNTAX INTEGER
				{
				disable(1),
				blacklist(2),
				whitelist(3)
				}
			MAX-ACCESS read-write
			STATUS current
			DESCRIPTION 
				"Description."
			::= { hwFatApGlobalConfig 3 }

		 --1.3.6.1.4.1.2011.6.139.11.1.63.1.4
		-- 1.3.6.1.4.1.2011.6.139.11.1.60.1.4
		hwFatApStaAccessModePorfile OBJECT-TYPE
			SYNTAX OCTET STRING (SIZE (1..35))
			MAX-ACCESS read-write
			STATUS current
			DESCRIPTION 
				"Description."
			::= { hwFatApGlobalConfig 4 }

		 --1.3.6.1.4.1.2011.6.139.11.1.63.1.5
		-- 1.3.6.1.4.1.2011.6.139.11.1.60.1.5
		hwFatApHighTempThreshold OBJECT-TYPE
			SYNTAX Unsigned32 (20..100|65535)
			MAX-ACCESS read-write
			STATUS current
			DESCRIPTION 
				"Description."
			::= { hwFatApGlobalConfig 5 }

		 --1.3.6.1.4.1.2011.6.139.11.1.63.1.6
		-- 1.3.6.1.4.1.2011.6.139.11.1.60.1.6
		hwFatApLowTempThreshold OBJECT-TYPE
			SYNTAX Integer32 (-70..10|65535)
			MAX-ACCESS read-write
			STATUS current
			DESCRIPTION 
				"Description."
			::= { hwFatApGlobalConfig 6 }

		 --1.3.6.1.4.1.2011.6.139.11.1.63.1.7
		-- 1.3.6.1.4.1.2011.6.139.11.1.60.1.7
		hwFatApDcaChannel5GBandwidth OBJECT-TYPE
			SYNTAX INTEGER
				{
				ht20(1),
				ht40(2),
				ht80(3)
				}
			MAX-ACCESS read-write
			STATUS current
			DESCRIPTION 
				"Description."
			::= { hwFatApGlobalConfig 7 }

		 --1.3.6.1.4.1.2011.6.139.11.1.63.1.8
		-- 1.3.6.1.4.1.2011.6.139.11.1.60.1.8
		hwFatApDcaChannel5GChannelSet OBJECT-TYPE
			SYNTAX OCTET STRING (SIZE (1..256))
			MAX-ACCESS read-write
			STATUS current
			DESCRIPTION 
				"Description."
			::= { hwFatApGlobalConfig 8 }

		 --1.3.6.1.4.1.2011.6.139.11.1.63.1.9
		-- 1.3.6.1.4.1.2011.6.139.11.1.60.1.9
		hwFatApDcaChannel2GChannelSet OBJECT-TYPE
			SYNTAX OCTET STRING (SIZE (1..256))
			MAX-ACCESS read-write
			STATUS current
			DESCRIPTION 
				"Description."
			::= { hwFatApGlobalConfig 9 }
 		 --1.3.6.1.4.1.2011.6.139.11.1.63.1.10
		-- 1.3.6.1.4.1.2011.6.139.11.1.60.1.10
		hwFatApDynamicBlackAgingTime OBJECT-TYPE
			SYNTAX Unsigned32 (180..3600)
			MAX-ACCESS read-write
			STATUS current
			DESCRIPTION 
				"Description."
			::= { hwFatApGlobalConfig 10 }
			
		--1.3.6.1.4.1.2011.6.139.11.1.63.1.11
		-- 1.3.6.1.4.1.2011.6.139.11.1.60.1.11
		hwFatApAntennaOutputMode OBJECT-TYPE
			SYNTAX INTEGER
				{
				combine(1),
				split(2)
				}
			MAX-ACCESS read-write
			STATUS current
			DESCRIPTION 
				"Description."
			::= { hwFatApGlobalConfig 11 }

		--1.3.6.1.4.1.2011.6.139.11.1.63.2
		-- 1.3.6.1.4.1.2011.6.139.11.1.60.2
		hwFatApRadioTable OBJECT-TYPE
			SYNTAX SEQUENCE OF HwFatApRadioEntry 
			MAX-ACCESS not-accessible
			STATUS current
			DESCRIPTION 
				"Description."
			::= { hwFatApConfigObjects 2 }

		--1.3.6.1.4.1.2011.6.139.11.1.63.2.1
		-- 1.3.6.1.4.1.2011.6.139.11.1.60.2.1
		hwFatApRadioEntry OBJECT-TYPE
			SYNTAX HwFatApRadioEntry 
			MAX-ACCESS not-accessible
			STATUS current
			DESCRIPTION 
				"Description."
			INDEX { hwFatApRadio }
			::= { hwFatApRadioTable 1 }


		HwFatApRadioEntry ::=
			SEQUENCE {				
				hwFatApRadio
					Unsigned32,
				hwFatApRadio0Frequency
					INTEGER,
				hwFatApRadio2gProfile
					OCTET STRING,
				hwFatApRadio5gProfile
					OCTET STRING,
				hwFatApRadioMeshProfile
					OCTET STRING,
				hwFatApLocationProfile
					OCTET STRING,
				hwFatApRadioRowStatus
					RowStatus,
				hwFatApMeshWhitelistProfile
					OCTET STRING,
				hwFatApWdsWhitelistProfile
					OCTET STRING,
				hwFatApRadioSwitch
					INTEGER,
				hwFatApRadioChannel
					Unsigned32,
				hwFatApRadioBandwidth
					INTEGER,
				hwFatApRadioEirp
					Unsigned32,
				hwFatApRadioAntennaGain
					Unsigned32,
				hwFatApRadioCoverageDistance
					Unsigned32,
				hwFatApRadioWorkMode
					INTEGER,
				hwFatApWidsDeviceDetectSwitch
					INTEGER,
				hwFatApWidsAttackDetectEnBmp
					Unsigned32,
				hwFatApWidsRogueContainSwitch
					INTEGER
			 }

		-- 1.3.6.1.4.1.2011.6.139.11.1.60.2.1.1
		hwFatApRadio OBJECT-TYPE
			SYNTAX Unsigned32 (0..1)
			MAX-ACCESS not-accessible
			STATUS current
			DESCRIPTION 
				"Description."
			::= { hwFatApRadioEntry 1 }

		-- 1.3.6.1.4.1.2011.6.139.11.1.60.2.1.2
		hwFatApRadio0Frequency OBJECT-TYPE
			SYNTAX INTEGER
				{
				frequency5G(1),
				frequency2G(2)
				}
			MAX-ACCESS read-write
			STATUS current
			DESCRIPTION 
				"Description."
			::= { hwFatApRadioEntry 2 }

		-- 1.3.6.1.4.1.2011.6.139.11.1.60.2.1.3
		hwFatApRadio2gProfile OBJECT-TYPE
			SYNTAX OCTET STRING (SIZE (1..35))
			MAX-ACCESS read-write
			STATUS current
			DESCRIPTION 
				"Description."
			::= { hwFatApRadioEntry 3 }

		-- 1.3.6.1.4.1.2011.6.139.11.1.60.2.1.4
		hwFatApRadio5gProfile OBJECT-TYPE
			SYNTAX OCTET STRING (SIZE (1..35))
			MAX-ACCESS read-write
			STATUS current
			DESCRIPTION 
				"Description."
			::= { hwFatApRadioEntry 4 }

		-- 1.3.6.1.4.1.2011.6.139.11.1.60.2.1.5
		hwFatApRadioMeshProfile OBJECT-TYPE
			SYNTAX OCTET STRING (SIZE (1..35))
			MAX-ACCESS read-write
			STATUS current
			DESCRIPTION 
				"Description."
			::= { hwFatApRadioEntry 5 }


		-- 1.3.6.1.4.1.2011.6.139.11.1.60.2.1.7
		hwFatApLocationProfile OBJECT-TYPE
			SYNTAX OCTET STRING (SIZE (1..35))
			MAX-ACCESS read-write
			STATUS current
			DESCRIPTION 
				"Description."
			::= { hwFatApRadioEntry 7 }

		-- 1.3.6.1.4.1.2011.6.139.11.1.60.2.1.8
		hwFatApRadioRowStatus OBJECT-TYPE
			SYNTAX RowStatus
			MAX-ACCESS read-write
			STATUS current
			DESCRIPTION 
				"Description."
			::= { hwFatApRadioEntry 8 }


		-- 1.3.6.1.4.1.2011.6.139.11.1.60.2.1.9
		hwFatApMeshWhitelistProfile OBJECT-TYPE
			SYNTAX OCTET STRING (SIZE (0..35))
			MAX-ACCESS read-write
			STATUS current
			DESCRIPTION
				"This object indicates the bound whitelist profile."
			::= { hwFatApRadioEntry 9 }


		-- 1.3.6.1.4.1.2011.6.139.11.1.60.2.1.10
		hwFatApWdsWhitelistProfile OBJECT-TYPE
			SYNTAX OCTET STRING (SIZE (0..35))
			MAX-ACCESS read-write
			STATUS current
			DESCRIPTION
				"This object indicates the bound whitelist profile."
			::= { hwFatApRadioEntry 10 }

		
		-- 1.3.6.1.4.1.2011.6.139.11.1.60.2.1.11
		hwFatApRadioSwitch OBJECT-TYPE
			SYNTAX INTEGER
				{
				disable(1),
				enable(2)
				}
			MAX-ACCESS read-write
			STATUS current
			DESCRIPTION
				"This object indicates the name of a 2G radio profile. It is the index of the table."
			::= { hwFatApRadioEntry 11 }

		
		-- 1.3.6.1.4.1.2011.6.139.11.1.60.2.1.12
		hwFatApRadioChannel OBJECT-TYPE
			SYNTAX Unsigned32
			MAX-ACCESS read-write
			STATUS current
			DESCRIPTION
				"This object indicates a radio-frequency channel. For 2.4G, the value ranges from 1 to 13. For 5G, the value ranges from 36 to 165 (with a separation interval of 4)."
			::= { hwFatApRadioEntry 12 }

		
		-- 1.3.6.1.4.1.2011.6.139.11.1.60.2.1.13
		hwFatApRadioBandwidth OBJECT-TYPE
			SYNTAX INTEGER
				{
				ht20(1),
				ht40Plus(2),
				ht40Minus(3),
				ht80(4)
				}
			MAX-ACCESS read-write
			STATUS current
			DESCRIPTION
				"This object indicate a bandwidth. The default value is 1."
			::= { hwFatApRadioEntry 13 }


		-- 1.3.6.1.4.1.2011.6.139.11.1.60.2.1.14
		hwFatApRadioEirp OBJECT-TYPE
			SYNTAX Unsigned32 (1..127)
			MAX-ACCESS read-write
			STATUS current
			DESCRIPTION
				"This object indicates a power value. The default value is 127. The configuration is saved but the actual power is determined by the maximum power supported by the AP."
			::= { hwFatApRadioEntry 14 }


		-- 1.3.6.1.4.1.2011.6.139.11.1.60.2.1.15
		hwFatApRadioAntennaGain OBJECT-TYPE
			SYNTAX Unsigned32 (0..30 | 255)
			MAX-ACCESS read-write
			STATUS current
			DESCRIPTION
				"This object indicates antenna gains. The default value 0xFF indicates that the default gain of an AP is used. It is expressed in dB. Default gains vary with different types of APs."
			::= { hwFatApRadioEntry 15 }


		-- 1.3.6.1.4.1.2011.6.139.11.1.60.2.1.16
		hwFatApRadioCoverageDistance OBJECT-TYPE
			SYNTAX Unsigned32 (1..400)
			MAX-ACCESS read-write
			STATUS current
			DESCRIPTION
				"This object indicates a radio coverage distance. The default value is 3. The unit is 0.1 km."
			::= { hwFatApRadioEntry 16 }


		-- 1.3.6.1.4.1.2011.6.139.11.1.60.2.1.17
		hwFatApRadioWorkMode OBJECT-TYPE
			SYNTAX INTEGER
				{
				normal(1),
				monitor(2)
				}
			MAX-ACCESS read-write
			STATUS current
			DESCRIPTION
				"This object indicates the radio working mode. The default value is 1."
			::= { hwFatApRadioEntry 17 }


		-- 1.3.6.1.4.1.2011.6.139.11.1.60.2.1.18
		hwFatApWidsDeviceDetectSwitch OBJECT-TYPE
			SYNTAX INTEGER
				{
				disable(1),
				enable(2)
				}
			MAX-ACCESS read-write
			STATUS current
			DESCRIPTION
				"This object indicates the status of the device detection function. The default value is 1."
			::= { hwFatApRadioEntry 18 }


		-- 1.3.6.1.4.1.2011.6.139.11.1.60.2.1.19
		hwFatApWidsAttackDetectEnBmp OBJECT-TYPE
			SYNTAX Unsigned32
			MAX-ACCESS read-write
			STATUS current
			DESCRIPTION
				"This object indicates the bit map of the brute force attack switch. bit0:weak-iv, bit1:spoof, bit2:flood, bit3:wpa-psk, bit4:wpa2-psk, bit5:wapi-psk, bit6:wep-psk."
			::= { hwFatApRadioEntry 19 }


		-- 1.3.6.1.4.1.2011.6.139.11.1.60.2.1.20
		hwFatApWidsRogueContainSwitch OBJECT-TYPE
			SYNTAX INTEGER
				{
				disable(1),
				enable(2)
				}
			MAX-ACCESS read-write
			STATUS current
			DESCRIPTION
				"This object indicates the status of the device detection function. The default value is 1."
			::= { hwFatApRadioEntry 20 }


		-- 1.3.6.1.4.1.2011.6.139.11.1.60.3
		hwFatApVapTable OBJECT-TYPE
			SYNTAX SEQUENCE OF HwFatApVapEntry 
			MAX-ACCESS not-accessible
			STATUS current
			DESCRIPTION 
				"Description."
			::= { hwFatApConfigObjects 3 }


		-- 1.3.6.1.4.1.2011.6.139.11.1.60.3.1
		hwFatApVapEntry OBJECT-TYPE
			SYNTAX HwFatApVapEntry 
			MAX-ACCESS not-accessible
			STATUS current
			DESCRIPTION 
				"Description."
			INDEX { hwFatApWlanId, hwFatApRadioId }
			::= { hwFatApVapTable 1 }


		HwFatApVapEntry ::=
			SEQUENCE {				
				hwFatApWlanId
					Unsigned32,
				hwFatApRadioId
					Unsigned32,
				hwFatApVapProfile
					OCTET STRING,
				hwFatApVapProfileRowStatus
					RowStatus 
			 }

		 --1.3.6.1.4.1.2011.6.139.11.1.63.3.1.1
		-- 1.3.6.1.4.1.2011.6.139.11.1.60.3.1.1
		hwFatApWlanId OBJECT-TYPE
			SYNTAX Unsigned32 (1..16)
			MAX-ACCESS not-accessible
			STATUS current
			DESCRIPTION 
				"Description."
			::= { hwFatApVapEntry 1 }

		 --1.3.6.1.4.1.2011.6.139.11.1.63.3.1.2
		-- 1.3.6.1.4.1.2011.6.139.11.1.60.3.1.2
		hwFatApRadioId OBJECT-TYPE
			SYNTAX Unsigned32 (0..1)
			MAX-ACCESS not-accessible
			STATUS current
			DESCRIPTION			 
		        	"Description."
			::= { hwFatApVapEntry 2 }
			
	     --1.3.6.1.4.1.2011.6.139.11.1.63.3.1.3
		-- 1.3.6.1.4.1.2011.6.139.11.1.60.3.1.3
		hwFatApVapProfile OBJECT-TYPE
			SYNTAX OCTET STRING (SIZE (1..35))
			MAX-ACCESS read-write
			STATUS current
			DESCRIPTION 
				"Description."
			::= { hwFatApVapEntry 3 }

		 --1.3.6.1.4.1.2011.6.139.11.1.63.3.1.4
		-- 1.3.6.1.4.1.2011.6.139.11.1.60.3.1.4
		hwFatApVapProfileRowStatus OBJECT-TYPE
			SYNTAX RowStatus
			MAX-ACCESS read-write
			STATUS current
			DESCRIPTION 
				"Description."
			::= { hwFatApVapEntry 4 } 
			
		--1.3.6.1.4.1.2011.6.139.11.1.61
		hwNAIRealmProfileListTable OBJECT-TYPE
			SYNTAX SEQUENCE OF HwNAIRealmProfileListEntry 
			MAX-ACCESS not-accessible
			STATUS current
			DESCRIPTION 
				"This table describes the NAI realm profile."
			::= { hwWlanConfigObjects 61 }

		--1.3.6.1.4.1.2011.6.139.11.1.61.1
		hwNAIRealmProfileListEntry OBJECT-TYPE
			SYNTAX HwNAIRealmProfileListEntry 
			MAX-ACCESS not-accessible
			STATUS current
			DESCRIPTION 
				"The index of this table is hwNAIRealmProfileListProfileName."
			INDEX { hwNAIRealmProfileListProfileName }
			::= { hwNAIRealmProfileListTable 1 }


		HwNAIRealmProfileListEntry ::=
			SEQUENCE {				
				hwNAIRealmProfileListProfileName
					OCTET STRING,
				hwNAIRealmProfileListRowStatus
					RowStatus 
			 }

		 --1.3.6.1.4.1.2011.6.139.11.1.61.1.1
		hwNAIRealmProfileListProfileName OBJECT-TYPE
			SYNTAX OCTET STRING (SIZE (1..35))
			MAX-ACCESS not-accessible
			STATUS current
			DESCRIPTION 
				"This object indicates the profile name."
			::= { hwNAIRealmProfileListEntry 1 }     
			
		 --1.3.6.1.4.1.2011.6.139.11.1.61.1.2
		hwNAIRealmProfileListRowStatus OBJECT-TYPE
			SYNTAX RowStatus
			MAX-ACCESS read-write
			STATUS current
			DESCRIPTION 
				"This object indicates the row status of this table. createAndGo(4) and destroy(6) are commonly used."
			::= { hwNAIRealmProfileListEntry 2 }     
			  
			  
		--1.3.6.1.4.1.2011.6.139.11.1.62
		hwWidsSpoofProfileListTable OBJECT-TYPE
			SYNTAX SEQUENCE OF HwWidsSpoofProfileListEntry 
			MAX-ACCESS not-accessible
			STATUS current
			DESCRIPTION 
				"This table is used to create or delete WIDS spoof SSID profiles."
			::= { hwWlanConfigObjects 62 }

		--1.3.6.1.4.1.2011.6.139.11.1.62.1
		hwWidsSpoofProfileListEntry OBJECT-TYPE
			SYNTAX HwWidsSpoofProfileListEntry 
			MAX-ACCESS not-accessible
			STATUS current
			DESCRIPTION 
				"The index of this table is hwWidsSpoofProfileListProfileName."
			INDEX { hwWidsSpoofProfileListProfileName }
			::= { hwWidsSpoofProfileListTable 1 }


		HwWidsSpoofProfileListEntry ::=
			SEQUENCE {				
				hwWidsSpoofProfileListProfileName
					OCTET STRING,
				hwWidsSpoofProfileListRowStatus
					RowStatus 
			 }

		 --1.3.6.1.4.1.2011.6.139.11.1.62.1.1
		hwWidsSpoofProfileListProfileName OBJECT-TYPE
			SYNTAX OCTET STRING (SIZE (1..35))
			MAX-ACCESS not-accessible
			STATUS current
			DESCRIPTION 
				"This object indicates the name of a WIDS spoof SSID profile."
			::= { hwWidsSpoofProfileListEntry 1 }     
			
		 --1.3.6.1.4.1.2011.6.139.11.1.62.1.2
		hwWidsSpoofProfileListRowStatus OBJECT-TYPE
			SYNTAX RowStatus
			MAX-ACCESS read-write
			STATUS current
			DESCRIPTION 
				"This object indicates the row status of this table. createAndGo(4) and destroy(6) are commonly used."
			::= { hwWidsSpoofProfileListEntry 2 }     
			
		--1.3.6.1.4.1.2011.6.139.11.1.63
		hwWidsWhitelistProfileListTable OBJECT-TYPE
			SYNTAX SEQUENCE OF HwWidsWhitelistProfileListEntry 
			MAX-ACCESS not-accessible
			STATUS current
			DESCRIPTION 
				"This table is used to create or delete WIDS confident profiles."
			::= { hwWlanConfigObjects 63 }

		--1.3.6.1.4.1.2011.6.139.11.1.63.1
		hwWidsWhitelistProfileListEntry OBJECT-TYPE
			SYNTAX HwWidsWhitelistProfileListEntry 
			MAX-ACCESS not-accessible
			STATUS current
			DESCRIPTION 
				"The index of this table is hwWidsWhitelistProfileListProfileName."
			INDEX { hwWidsWhitelistProfileListProfileName }
			::= { hwWidsWhitelistProfileListTable 1 }


		HwWidsWhitelistProfileListEntry ::=
			SEQUENCE {				
				hwWidsWhitelistProfileListProfileName
					OCTET STRING,
				hwWidsWhitelistProfileListRowStatus
					RowStatus 
			 }

		 --1.3.6.1.4.1.2011.6.139.11.1.63.1.1
		hwWidsWhitelistProfileListProfileName OBJECT-TYPE
			SYNTAX OCTET STRING (SIZE (1..35))
			MAX-ACCESS not-accessible
			STATUS current
			DESCRIPTION 
				"This object indicates the name of a WIDS confident profile."
			::= { hwWidsWhitelistProfileListEntry 1 }     
			
		 --1.3.6.1.4.1.2011.6.139.11.1.63.1.2
		hwWidsWhitelistProfileListRowStatus OBJECT-TYPE
			SYNTAX RowStatus
			MAX-ACCESS read-write
			STATUS current
			DESCRIPTION 
				"This object indicates the row status of this table. createAndGo(4) and destroy(6) are commonly used."
			::= { hwWidsWhitelistProfileListEntry 2 }

		
		-- 1.3.6.1.4.1.2011.6.139.11.1.64
		hwWlanLoadBalanceStaticGroupTable OBJECT-TYPE
			SYNTAX SEQUENCE OF HwWlanLoadBalanceStaticGroupEntry
			MAX-ACCESS not-accessible
			STATUS current
			DESCRIPTION
				"This table records information about the static load balancing group."
			::= { hwWlanConfigObjects 64 }

		
		-- 1.3.6.1.4.1.2011.6.139.11.1.64.1
		hwWlanLoadBalanceStaticGroupEntry OBJECT-TYPE
			SYNTAX HwWlanLoadBalanceStaticGroupEntry
			MAX-ACCESS not-accessible
			STATUS current
			DESCRIPTION
				"The index of this table is hwWlanLBGroupName."
			INDEX { hwWlanLBGroupName }
			::= { hwWlanLoadBalanceStaticGroupTable 1 }

		
		HwWlanLoadBalanceStaticGroupEntry ::=
			SEQUENCE { 
				hwWlanLBGroupName
					OCTET STRING,
				hwWlanLBGapThreshold
					Unsigned32,
				hwWlanLBDenyThreshold
					Unsigned32,
				hwWlanLBStartThreshold
					Unsigned32,
				hwWlanLBGroupStatus
					Unsigned32,
				hwWlanLBGroupRowStatus
					RowStatus
			 }

		-- 1.3.6.1.4.1.2011.6.139.11.1.64.1.1
		hwWlanLBGroupName OBJECT-TYPE
			SYNTAX OCTET STRING
			MAX-ACCESS not-accessible
			STATUS current
			DESCRIPTION
				"This object indicates the name of the static load balancing group."
			::= { hwWlanLoadBalanceStaticGroupEntry 1 }

		
		-- 1.3.6.1.4.1.2011.6.139.11.1.64.1.2
		hwWlanLBGapThreshold OBJECT-TYPE
			SYNTAX Unsigned32
			MAX-ACCESS read-write
			STATUS current
			DESCRIPTION
				"This object indicates the load difference threshold of a static load balancing group."
			::= { hwWlanLoadBalanceStaticGroupEntry 2 }

		
		-- 1.3.6.1.4.1.2011.6.139.11.1.64.1.3
		hwWlanLBDenyThreshold OBJECT-TYPE
			SYNTAX Unsigned32
			MAX-ACCESS read-write
			STATUS current
			DESCRIPTION
				"This object indicates the maximum number of times an AP rejects association requests of a STA in the static load balancing group."
			::= { hwWlanLoadBalanceStaticGroupEntry 3 }

		
		-- 1.3.6.1.4.1.2011.6.139.11.1.64.1.4
		hwWlanLBStartThreshold OBJECT-TYPE
			SYNTAX Unsigned32
			MAX-ACCESS read-write
			STATUS current
			DESCRIPTION
				"This object indicates the start threshold for load balancing in a static load balancing group."
			::= { hwWlanLoadBalanceStaticGroupEntry 4 }

		
		-- 1.3.6.1.4.1.2011.6.139.11.1.64.1.5
		hwWlanLBGroupStatus OBJECT-TYPE
			SYNTAX Unsigned32
			MAX-ACCESS read-only
			STATUS current
			DESCRIPTION
				"This object indicates the load balancing status in the static load balancing group.1: Load is not balanced.2: Load is balanced."
			::= { hwWlanLoadBalanceStaticGroupEntry 5 }

		
		-- 1.3.6.1.4.1.2011.6.139.11.1.64.1.6
		hwWlanLBGroupRowStatus OBJECT-TYPE
			SYNTAX RowStatus
			MAX-ACCESS read-write
			STATUS current
			DESCRIPTION
				"This object indicates the row status of this table, which can be createAndGo(4) or destroy(6)."
			::= { hwWlanLoadBalanceStaticGroupEntry 6 }

		
		-- 1.3.6.1.4.1.2011.6.139.11.1.65
		hwWlanLoadBalanceStaticGroupMemberTable OBJECT-TYPE
			SYNTAX SEQUENCE OF HwWlanLoadBalanceStaticGroupMemberEntry
			MAX-ACCESS not-accessible
			STATUS current
			DESCRIPTION
				"This table records information about members in the static load balancing group."
			::= { hwWlanConfigObjects 65 }

		
		-- 1.3.6.1.4.1.2011.6.139.11.1.65.1
		hwWlanLoadBalanceStaticGroupMemberEntry OBJECT-TYPE
			SYNTAX HwWlanLoadBalanceStaticGroupMemberEntry
			MAX-ACCESS not-accessible
			STATUS current
			DESCRIPTION
				"The indexes of this table are hwWlanLBGroupName, hwWlanApName, and hwWlanRadioID."
			INDEX { hwWlanLBGroupName, hwWlanApName, hwWlanRadioID }
			::= { hwWlanLoadBalanceStaticGroupMemberTable 1 }

		
		HwWlanLoadBalanceStaticGroupMemberEntry ::=
			SEQUENCE { 
				hwWlanLBMemberRowStatus
					RowStatus
			 }

		-- 1.3.6.1.4.1.2011.6.139.11.1.65.1.1
		hwWlanLBMemberRowStatus OBJECT-TYPE
			SYNTAX RowStatus
			MAX-ACCESS read-write
			STATUS current
			DESCRIPTION
				"This object indicates the row status of this table."
			::= { hwWlanLoadBalanceStaticGroupMemberEntry 1 }

		
		-- 1.3.6.1.4.1.2011.6.139.11.1.66
		hwWlanCountryCodeTable OBJECT-TYPE
			SYNTAX SEQUENCE OF HwWlanCountryCodeEntry
			MAX-ACCESS not-accessible
			STATUS current
			DESCRIPTION
				"Description."
			::= { hwWlanConfigObjects 66 }

		
		-- 1.3.6.1.4.1.2011.6.139.11.1.66.1
		hwWlanCountryCodeEntry OBJECT-TYPE
			SYNTAX HwWlanCountryCodeEntry
			MAX-ACCESS not-accessible
			STATUS current
			DESCRIPTION
				"Description."
			INDEX { hwWlanCountryCode }
			::= { hwWlanCountryCodeTable 1 }

		
		HwWlanCountryCodeEntry ::=
			SEQUENCE { 
				hwWlanCountryCode
					OCTET STRING,
				hwWlanCountryCodeEngDescription
					OCTET STRING,
				hwWlanCountryCodeAvailableChannelSet2gBW20
					OCTET STRING,
				hwWlanCountryCodeAvailableChannelSet2gBW40Plus
					OCTET STRING,
				hwWlanCountryCodeAvailableChannelSet2gBW40Minus
					OCTET STRING,
				hwWlanCountryCodeAvailableChannelSet5gBW20
					OCTET STRING,
				hwWlanCountryCodeAvailableChannelSet5gBW40Plus
					OCTET STRING,
				hwWlanCountryCodeAvailableChannelSet5gBW40Minus
					OCTET STRING,
				hwWlanCountryCodeAvailableChannelSet5gBW80
					OCTET STRING,
				hwWlanCountryCodeAvailableChannelSet5gBW160
					OCTET STRING
			 }

		-- 1.3.6.1.4.1.2011.6.139.11.1.66.1.1
		hwWlanCountryCode OBJECT-TYPE
			SYNTAX OCTET STRING (SIZE (0..255))
			MAX-ACCESS not-accessible
			STATUS current
			DESCRIPTION
				"Description."
			::= { hwWlanCountryCodeEntry 1 }

		
		-- 1.3.6.1.4.1.2011.6.139.11.1.66.1.2
		hwWlanCountryCodeEngDescription OBJECT-TYPE
			SYNTAX OCTET STRING (SIZE (0..255))
			MAX-ACCESS read-only
			STATUS current
			DESCRIPTION
				"Description."
			::= { hwWlanCountryCodeEntry 2 }

		
		-- 1.3.6.1.4.1.2011.6.139.11.1.66.1.3
		hwWlanCountryCodeAvailableChannelSet2gBW20 OBJECT-TYPE
			SYNTAX OCTET STRING (SIZE (0..255))
			MAX-ACCESS read-only
			STATUS current
			DESCRIPTION
				"Description."
			::= { hwWlanCountryCodeEntry 3 }

		
		-- 1.3.6.1.4.1.2011.6.139.11.1.66.1.4
		hwWlanCountryCodeAvailableChannelSet2gBW40Plus OBJECT-TYPE
			SYNTAX OCTET STRING (SIZE (0..255))
			MAX-ACCESS read-only
			STATUS current
			DESCRIPTION
				"Description."
			::= { hwWlanCountryCodeEntry 4 }

		
		-- 1.3.6.1.4.1.2011.6.139.11.1.66.1.5
		hwWlanCountryCodeAvailableChannelSet2gBW40Minus OBJECT-TYPE
			SYNTAX OCTET STRING (SIZE (0..255))
			MAX-ACCESS read-only
			STATUS current
			DESCRIPTION
				"Description."
			::= { hwWlanCountryCodeEntry 5 }

		
		-- 1.3.6.1.4.1.2011.6.139.11.1.66.1.6
		hwWlanCountryCodeAvailableChannelSet5gBW20 OBJECT-TYPE
			SYNTAX OCTET STRING (SIZE (0..255))
			MAX-ACCESS read-only
			STATUS current
			DESCRIPTION
				"Description."
			::= { hwWlanCountryCodeEntry 6 }

		
		-- 1.3.6.1.4.1.2011.6.139.11.1.66.1.7
		hwWlanCountryCodeAvailableChannelSet5gBW40Plus OBJECT-TYPE
			SYNTAX OCTET STRING (SIZE (0..255))
			MAX-ACCESS read-only
			STATUS current
			DESCRIPTION
				"Description."
			::= { hwWlanCountryCodeEntry 7 }

		
		-- 1.3.6.1.4.1.2011.6.139.11.1.66.1.8
		hwWlanCountryCodeAvailableChannelSet5gBW40Minus OBJECT-TYPE
			SYNTAX OCTET STRING (SIZE (0..255))
			MAX-ACCESS read-only
			STATUS current
			DESCRIPTION
				"Description."
			::= { hwWlanCountryCodeEntry 8 }

		
		-- 1.3.6.1.4.1.2011.6.139.11.1.66.1.9
		hwWlanCountryCodeAvailableChannelSet5gBW80 OBJECT-TYPE
			SYNTAX OCTET STRING (SIZE (0..255))
			MAX-ACCESS read-only
			STATUS current
			DESCRIPTION
				"Description."
			::= { hwWlanCountryCodeEntry 9 }
			
		-- 1.3.6.1.4.1.2011.6.139.11.1.66.1.10
		hwWlanCountryCodeAvailableChannelSet5gBW160 OBJECT-TYPE
			SYNTAX OCTET STRING (SIZE (0..255))
			MAX-ACCESS read-only
			STATUS current
			DESCRIPTION
				"Description."
			::= { hwWlanCountryCodeEntry 10 }			

		--1.3.6.1.4.1.2011.6.139.11.1.67
		hwUCCProfileTable OBJECT-TYPE
			SYNTAX SEQUENCE OF HwUCCProfileEntry 
			MAX-ACCESS not-accessible
			STATUS current
			DESCRIPTION 
				"This table is used to configure and query UCC profile parameters."
			::= { hwWlanConfigObjects 67 }

		--1.3.6.1.4.1.2011.6.139.11.1.67.1
		hwUCCProfileEntry OBJECT-TYPE
			SYNTAX HwUCCProfileEntry 
			MAX-ACCESS not-accessible
			STATUS current
			DESCRIPTION 
				"The index of this table is hwUCCProfileName."
			INDEX { hwUCCProfileName }
			::= { hwUCCProfileTable 1 }


		HwUCCProfileEntry ::=
			SEQUENCE {				
				hwUCCProfileName
					OCTET STRING,
				hwUCCProfLyncVoice8021p
					INTEGER,
				hwUCCProfLyncVoice8021pValue
					Unsigned32,
				hwUCCProfLyncVoiceDscp
					INTEGER,
				hwUCCProfLyncVoiceDscpValue
					Unsigned32,
				hwUCCProfLyncVideo8021p
					INTEGER,
				hwUCCProfLyncVideo8021pValue
					Unsigned32,
				hwUCCProfLyncVideoDscp
					INTEGER,
				hwUCCProfLyncVideoDscpValue
					Unsigned32,					
				hwUCCProfLyncShare8021p
					INTEGER,
				hwUCCProfLyncShare8021pValue
					Unsigned32,
				hwUCCProfLyncShareDscp
					INTEGER,
				hwUCCProfLyncShareDscpValue
					Unsigned32,
				hwUCCProfLyncFileTransfer8021p
					INTEGER,
				hwUCCProfLyncFileTransfer8021pValue
					Unsigned32,
				hwUCCProfLyncFileTransferDscp
					INTEGER,
				hwUCCProfLyncFileTransferDscpValue
					Unsigned32,				
			        hwUCCProfileRowStatus
					RowStatus 
			 }

		 --1.3.6.1.4.1.2011.6.139.11.1.67.1.1
		hwUCCProfileName OBJECT-TYPE
			SYNTAX OCTET STRING (SIZE (1..35))
			MAX-ACCESS not-accessible
			STATUS current
			DESCRIPTION 
				"This object indicates the name of a UCC profile. It is the index of the table."
			::= { hwUCCProfileEntry 1 }

		 --1.3.6.1.4.1.2011.6.139.11.1.67.1.2
		hwUCCProfLyncVoice8021p OBJECT-TYPE
			SYNTAX INTEGER
				{
				disable(1),
				enable(2)
				}
			MAX-ACCESS read-write
			STATUS current
			DESCRIPTION 
				"This object indicates the switch of lync-voice remark 8021p."
			::= { hwUCCProfileEntry 2 }
			
		 --1.3.6.1.4.1.2011.6.139.11.1.67.1.3
		hwUCCProfLyncVoice8021pValue OBJECT-TYPE
			SYNTAX Unsigned32 (0..7)
			MAX-ACCESS read-write
			STATUS current
			DESCRIPTION 
				"This object indicates the value of lync-voice remark 8021p."
			::= { hwUCCProfileEntry 3 }

		 --1.3.6.1.4.1.2011.6.139.11.1.67.1.4
		hwUCCProfLyncVoiceDscp OBJECT-TYPE
			SYNTAX INTEGER
				{
				disable(1),
				enable(2)
				}
			MAX-ACCESS read-write
			STATUS current
			DESCRIPTION 
				"This object indicates the switch of lync-voice remark dscp."
			::= { hwUCCProfileEntry 4 }

		 --1.3.6.1.4.1.2011.6.139.11.1.67.1.5
		hwUCCProfLyncVoiceDscpValue OBJECT-TYPE
			SYNTAX Unsigned32 (0..63)
			MAX-ACCESS read-write
			STATUS current
			DESCRIPTION 
				"This object indicates the value of lync-voice remark dscp."
			::= { hwUCCProfileEntry 5 }
			
		 --1.3.6.1.4.1.2011.6.139.11.1.67.1.6
		hwUCCProfLyncVideo8021p OBJECT-TYPE
			SYNTAX INTEGER
				{
				disable(1),
				enable(2)
				}
			MAX-ACCESS read-write
			STATUS current
			DESCRIPTION 
				"This object indicates the switch of lync-video remark 8021p."
			::= { hwUCCProfileEntry 6 }
			
		 --1.3.6.1.4.1.2011.6.139.11.1.67.1.7
		hwUCCProfLyncVideo8021pValue OBJECT-TYPE
			SYNTAX Unsigned32 (0..7)
			MAX-ACCESS read-write
			STATUS current
			DESCRIPTION 
				"This object indicates the value of lync-video remark 8021p."
			::= { hwUCCProfileEntry 7 }

		 --1.3.6.1.4.1.2011.6.139.11.1.67.1.8
		hwUCCProfLyncVideoDscp OBJECT-TYPE
			SYNTAX INTEGER
				{
				disable(1),
				enable(2)
				}
			MAX-ACCESS read-write
			STATUS current
			DESCRIPTION 
				"This object indicates the switch of lync-video remark dscp."
			::= { hwUCCProfileEntry 8 }

		 --1.3.6.1.4.1.2011.6.139.11.1.67.1.9
		hwUCCProfLyncVideoDscpValue OBJECT-TYPE
			SYNTAX Unsigned32 (0..63)
			MAX-ACCESS read-write
			STATUS current
			DESCRIPTION 
				"This object indicates the value of lync-video remark dscp."
			::= { hwUCCProfileEntry 9 }

		 --1.3.6.1.4.1.2011.6.139.11.1.67.1.10
		hwUCCProfLyncShare8021p OBJECT-TYPE
			SYNTAX INTEGER
				{
				disable(1),
				enable(2)
				}
			MAX-ACCESS read-write
			STATUS current
			DESCRIPTION 
				"This object indicates the switch of lync-destop-share remark 8021p."
			::= { hwUCCProfileEntry 10 }
			
		 --1.3.6.1.4.1.2011.6.139.11.1.67.1.11
		hwUCCProfLyncShare8021pValue OBJECT-TYPE
			SYNTAX Unsigned32 (0..7)
			MAX-ACCESS read-write
			STATUS current
			DESCRIPTION 
				"This object indicates the value of lync-destop-share remark 8021p."
			::= { hwUCCProfileEntry 11 }

		 --1.3.6.1.4.1.2011.6.139.11.1.67.1.12
		hwUCCProfLyncShareDscp OBJECT-TYPE
			SYNTAX INTEGER
				{
				disable(1),
				enable(2)
				}
			MAX-ACCESS read-write
			STATUS current
			DESCRIPTION 
				"This object indicates the switch of lync-destop-share remark dscp."
			::= { hwUCCProfileEntry 12 }

		 --1.3.6.1.4.1.2011.6.139.11.1.67.1.13
		hwUCCProfLyncShareDscpValue OBJECT-TYPE
			SYNTAX Unsigned32 (0..63)
			MAX-ACCESS read-write
			STATUS current
			DESCRIPTION 
				"This object indicates the value of lync-destop-share remark dscp."
			::= { hwUCCProfileEntry 13 }
			
		 --1.3.6.1.4.1.2011.6.139.11.1.67.1.14
		hwUCCProfLyncFileTransfer8021p OBJECT-TYPE
			SYNTAX INTEGER
				{
				disable(1),
				enable(2)
				}
			MAX-ACCESS read-write
			STATUS current
			DESCRIPTION 
				"This object indicates the switch of lync-file-transfer remark 8021p."
			::= { hwUCCProfileEntry 14 }
			
		 --1.3.6.1.4.1.2011.6.139.11.1.67.1.15
		hwUCCProfLyncFileTransfer8021pValue OBJECT-TYPE
			SYNTAX Unsigned32 (0..7)
			MAX-ACCESS read-write
			STATUS current
			DESCRIPTION 
				"This object indicates the value of lync-file-transfer remark 8021p."
			::= { hwUCCProfileEntry 15 }

		 --1.3.6.1.4.1.2011.6.139.11.1.67.1.16
		hwUCCProfLyncFileTransferDscp OBJECT-TYPE
			SYNTAX INTEGER
				{
				disable(1),
				enable(2)
				}
			MAX-ACCESS read-write
			STATUS current
			DESCRIPTION 
				"This object indicates the switch of lync-file-transfer remark dscp."
			::= { hwUCCProfileEntry 16 }

		 --1.3.6.1.4.1.2011.6.139.11.1.67.1.17
		hwUCCProfLyncFileTransferDscpValue OBJECT-TYPE
			SYNTAX Unsigned32 (0..63)
			MAX-ACCESS read-write
			STATUS current
			DESCRIPTION 
				"This object indicates the value of lync-file-transfer remark dscp."
			::= { hwUCCProfileEntry 17 }

		 --1.3.6.1.4.1.2011.6.139.11.1.67.1.18
		hwUCCProfileRowStatus OBJECT-TYPE
			SYNTAX RowStatus
			MAX-ACCESS read-write
			STATUS current
			DESCRIPTION 
				"This object indicates the row status of this table. ROWSTATUS_CREATEANDFLOW and ROWSTATUS_DESTROY are commonly used."
			::= { hwUCCProfileEntry 18 }
		
		-- 1.3.6.1.4.1.2011.6.139.11.1.68
		hwSoftgreProfileTable OBJECT-TYPE
			SYNTAX SEQUENCE OF HwSoftgreProfileEntry
			MAX-ACCESS not-accessible
			STATUS current
			DESCRIPTION
				"Description."
			::= { hwWlanConfigObjects 68 }

		
		-- 1.3.6.1.4.1.2011.6.139.11.1.68.1
		hwSoftgreProfileEntry OBJECT-TYPE
			SYNTAX HwSoftgreProfileEntry
			MAX-ACCESS not-accessible
			STATUS current
			DESCRIPTION
				"Description."
			INDEX { hwSoftgreProfileName }
			::= { hwSoftgreProfileTable 1 }

		
		HwSoftgreProfileEntry ::=
			SEQUENCE { 
				hwSoftgreProfileName
					OCTET STRING,
				hwSoftgreDestinationIPAddress
					IpAddress,
				hwSoftgreDestinationIPv6Address
					OCTET STRING,
				hwSoftgreKeepaliveFlag
					INTEGER,
				hwSoftgreKeepalivePeriod
					Unsigned32,
				hwSoftgreKeepaliveRetryTimes
					Unsigned32,
				hwSoftgreProfileRowStatus
					RowStatus
			 }

		-- 1.3.6.1.4.1.2011.6.139.11.1.68.1.1
		hwSoftgreProfileName OBJECT-TYPE
			SYNTAX OCTET STRING (SIZE (1..35))
			MAX-ACCESS not-accessible
			STATUS current
			DESCRIPTION
				"Description."
			::= { hwSoftgreProfileEntry 1 }

		
		-- 1.3.6.1.4.1.2011.6.139.11.1.68.1.2
		hwSoftgreDestinationIPAddress OBJECT-TYPE
			SYNTAX IpAddress
			MAX-ACCESS read-write
			STATUS current
			DESCRIPTION
				"Description."
			::= { hwSoftgreProfileEntry 2 }

		
		-- 1.3.6.1.4.1.2011.6.139.11.1.68.1.3
		hwSoftgreDestinationIPv6Address OBJECT-TYPE
			SYNTAX OCTET STRING
			MAX-ACCESS read-write
			STATUS current
			DESCRIPTION
				"Description."
			::= { hwSoftgreProfileEntry 3 }

		
		-- 1.3.6.1.4.1.2011.6.139.11.1.68.1.4
		hwSoftgreKeepaliveFlag OBJECT-TYPE
			SYNTAX INTEGER
				{
				disable(1),
				enable(2)
				}
			MAX-ACCESS read-write
			STATUS current
			DESCRIPTION
				"Description."
			::= { hwSoftgreProfileEntry 4 }

		
		-- 1.3.6.1.4.1.2011.6.139.11.1.68.1.5
		hwSoftgreKeepalivePeriod OBJECT-TYPE
			SYNTAX Unsigned32 (1..32767)
			MAX-ACCESS read-write
			STATUS current
			DESCRIPTION
				"Description."
			::= { hwSoftgreProfileEntry 5 }

		
		-- 1.3.6.1.4.1.2011.6.139.11.1.68.1.6
		hwSoftgreKeepaliveRetryTimes OBJECT-TYPE
			SYNTAX Unsigned32 (1..255)
			MAX-ACCESS read-write
			STATUS current
			DESCRIPTION
				"Description."
			::= { hwSoftgreProfileEntry 6 }

		
		-- 1.3.6.1.4.1.2011.6.139.11.1.68.1.7
		hwSoftgreProfileRowStatus OBJECT-TYPE
			SYNTAX RowStatus
			MAX-ACCESS read-write
			STATUS current
			DESCRIPTION
				"Description."
			::= { hwSoftgreProfileEntry 7 }
		--1.3.6.1.4.1.2011.6.139.11.1.69
		hwWlanIDIndexedAPSpecificTable OBJECT-TYPE
			SYNTAX SEQUENCE OF HwWlanIDIndexedAPSpecificEntry
			MAX-ACCESS not-accessible
			STATUS current
			DESCRIPTION 
				"This table is used to create or delete an AP specific profile and bind an AP system profile, 2G radio profile, or domain profile to it or unbind an AP system profile, 2G radio profile, or domain profile from it."
			::= { hwWlanConfigObjects 69 }
		--1.3.6.1.4.1.2011.6.139.11.1.69.1
		hwWlanIDIndexedAPSpecificEntry OBJECT-TYPE
			SYNTAX HwWlanIDIndexedAPSpecificEntry 
			MAX-ACCESS not-accessible
			STATUS current
			DESCRIPTION 
				"The index of this table is hwWlanIDIndexedAPSpApId."
			INDEX { hwWlanIDIndexedAPSpApId }
			::= { hwWlanIDIndexedAPSpecificTable 1 }
		HwWlanIDIndexedAPSpecificEntry ::=
			SEQUENCE { 
				hwWlanIDIndexedAPSpApId
					Unsigned32,
				hwWlanIDIndexedAPSpAPSystemProfile
					OCTET STRING,
				hwWlanIDIndexedAPSpDomainProfile
					OCTET STRING,				
				hwWlanIDIndexedAPSpApMac
					MacAddress,				
				hwWlanIDIndexedAPSpApTypeInfo
					OCTET STRING,
				hwWlanIDIndexedAPSpWidsProfile
					OCTET STRING,
				hwWlanIDIndexedAPSpRowStatus
					RowStatus
			 }
		-- 1.3.6.1.4.1.2011.6.139.11.1.69.1.1
		hwWlanIDIndexedAPSpApId OBJECT-TYPE
			SYNTAX Unsigned32
			MAX-ACCESS not-accessible
			STATUS current
			DESCRIPTION
				"This object indicates the AP ID."
			::= { hwWlanIDIndexedAPSpecificEntry 1 }
		-- 1.3.6.1.4.1.2011.6.139.11.1.69.1.2
		hwWlanIDIndexedAPSpAPSystemProfile OBJECT-TYPE
			SYNTAX OCTET STRING (SIZE (0..35))
			MAX-ACCESS read-write
			STATUS current
			DESCRIPTION 
				"This object indicates the system profile bound to the AP specific profile."
			::= { hwWlanIDIndexedAPSpecificEntry 2 }
		-- 1.3.6.1.4.1.2011.6.139.11.1.69.1.3
		hwWlanIDIndexedAPSpDomainProfile OBJECT-TYPE
			SYNTAX OCTET STRING (SIZE (0..35))
			MAX-ACCESS read-write
			STATUS current
			DESCRIPTION 
				"This object indicates the domain profile bound to the AP specific profile."
			::= { hwWlanIDIndexedAPSpecificEntry 3 }
		-- 1.3.6.1.4.1.2011.6.139.11.1.69.1.4
		hwWlanIDIndexedAPSpApMac OBJECT-TYPE
			SYNTAX MacAddress
			MAX-ACCESS read-write
			STATUS current
			DESCRIPTION
				"This object indicates the MAC address of an AP."
			::= { hwWlanIDIndexedAPSpecificEntry 4 }
		-- 1.3.6.1.4.1.2011.6.139.11.1.69.1.5
		hwWlanIDIndexedAPSpApTypeInfo OBJECT-TYPE
			SYNTAX OCTET STRING (SIZE (0..35))
			MAX-ACCESS read-write
			STATUS current
			DESCRIPTION
				"This object indicates the domain profile bound to the AP specific profile."
			::= { hwWlanIDIndexedAPSpecificEntry 5 }
		-- 1.3.6.1.4.1.2011.6.139.11.1.69.1.6
		hwWlanIDIndexedAPSpWidsProfile OBJECT-TYPE
			SYNTAX OCTET STRING (SIZE (0..35))
			MAX-ACCESS read-write
			STATUS current
			DESCRIPTION
				"This object indicates the bound WIDS profile."
			::= { hwWlanIDIndexedAPSpecificEntry 6 }
		-- 1.3.6.1.4.1.2011.6.139.11.1.69.1.7
		hwWlanIDIndexedAPSpRowStatus OBJECT-TYPE
			SYNTAX RowStatus
			MAX-ACCESS read-write
			STATUS current
			DESCRIPTION 
				"This object indicates the row status of this table. ROWSTATUS_CREATEANDFLOW and ROWSTATUS_DESTROY are commonly used?	ROWSTATUS_UNDEFINED: undefined ?	ROWSTATUS_ACTIVE: active ?	ROWSTATUS_NOTINSERVICE: notInService ?	ROWSTATUS_NOTREADY: notReady ?	ROWSTATUS_CREATEANDFLOW: createAndGo ?	ROWSTATUS_CREATEANDWAIT: createAndWait ?	ROWSTATUS_DESTROY: destroy."
			::= { hwWlanIDIndexedAPSpecificEntry 7 }
		-- 1.3.6.1.4.1.2011.6.139.11.1.70
		hwIDIndexedAPSpecificWiredPortTable OBJECT-TYPE
			SYNTAX SEQUENCE OF HwIDIndexedAPSpecificWiredPortEntry 
			MAX-ACCESS not-accessible
			STATUS current
			DESCRIPTION 
				"This table is used to bind an AP wired port profile to an AP specific profile or unbind an AP wired port profile from an AP specific profile.."
			::= { hwWlanConfigObjects 70 }
		--1.3.6.1.4.1.2011.6.139.11.1.70.1
		hwIDIndexedAPSpecificWiredPortEntry OBJECT-TYPE
			SYNTAX HwIDIndexedAPSpecificWiredPortEntry 
			MAX-ACCESS not-accessible
			STATUS current
			DESCRIPTION 
				"Indexes of this table are  hwIDIndexedAPSpWPInterfaceType, hwIDIndexedAPSpWPInterfaceNum and hwWlanIDIndexedAPSpApId."
			INDEX { hwIDIndexedAPSpWPInterfaceType, hwIDIndexedAPSpWPInterfaceNum, hwWlanIDIndexedAPSpApId }
			::= { hwIDIndexedAPSpecificWiredPortTable 1 }
		HwIDIndexedAPSpecificWiredPortEntry ::=
			SEQUENCE {				
				hwIDIndexedAPSpWPInterfaceType
					INTEGER,
				hwIDIndexedAPSpWPInterfaceNum
					Unsigned32,
				hwIDIndexedAPSpWPProfile
					OCTET STRING,
				hwIDIndexedAPSpWPRowStatus
					RowStatus
			 }
		 --1.3.6.1.4.1.2011.6.139.11.1.70.1.1
		hwIDIndexedAPSpWPInterfaceType OBJECT-TYPE
			SYNTAX INTEGER
				{
				fe(1),
				ge(2) ,
				trunk(3)
				}
			MAX-ACCESS not-accessible
			STATUS current
			DESCRIPTION 
				"This object indicates the interface type."
			::= { hwIDIndexedAPSpecificWiredPortEntry 1 }
		 --1.3.6.1.4.1.2011.6.139.11.1.70.1.2
		hwIDIndexedAPSpWPInterfaceNum OBJECT-TYPE
			SYNTAX Unsigned32 (0..27)
			MAX-ACCESS not-accessible
			STATUS current
			DESCRIPTION 
				"This object indicates the interface index."
			::= { hwIDIndexedAPSpecificWiredPortEntry 2 }
		 --1.3.6.1.4.1.2011.6.139.11.1.70.1.3
		hwIDIndexedAPSpWPProfile OBJECT-TYPE
			SYNTAX OCTET STRING (SIZE (0..35))
			MAX-ACCESS read-write
			STATUS current
			DESCRIPTION 
				"This object indicates the bound wired port profile."
			::= { hwIDIndexedAPSpecificWiredPortEntry 3 }
		 --1.3.6.1.4.1.2011.6.139.11.1.70.1.4
		hwIDIndexedAPSpWPRowStatus OBJECT-TYPE
			SYNTAX RowStatus
			MAX-ACCESS read-write
			STATUS current
			DESCRIPTION 
				"This object indicates the row status of this table. ROWSTATUS_CREATEANDFLOW and ROWSTATUS_DESTROY are commonly used?	ROWSTATUS_UNDEFINED: undefined ?	ROWSTATUS_ACTIVE: active ?	ROWSTATUS_NOTINSERVICE: notInService ?	ROWSTATUS_NOTREADY: notReady ?	ROWSTATUS_CREATEANDFLOW: createAndGo ?	ROWSTATUS_CREATEANDWAIT: createAndWait ?	ROWSTATUS_DESTROY: destroy."
			::= { hwIDIndexedAPSpecificWiredPortEntry 4 }
		--1.3.6.1.4.1.2011.6.139.11.1.71
		hwIDIndexedAPSpecificRadioTable OBJECT-TYPE
			SYNTAX SEQUENCE OF HwIDIndexedAPSpecificRadioEntry 
			MAX-ACCESS not-accessible
			STATUS current
			DESCRIPTION 
				"This table records the information about profiles bound based on radio in an AP specific profile, including 5G radio profile, Mesh profile, WDS profile, WIDS profile, location profile, and spectrum profile."
			::= { hwWlanConfigObjects 71 }
		--1.3.6.1.4.1.2011.6.139.11.1.71.1
		hwIDIndexedAPSpecificRadioEntry OBJECT-TYPE
			SYNTAX HwIDIndexedAPSpecificRadioEntry 
			MAX-ACCESS not-accessible
			STATUS current
			DESCRIPTION 
				"Indexes of this table are hwIDIndexedAPSpRadio and hwWlanIDIndexedAPSpApId."
			INDEX { hwIDIndexedAPSpRadio, hwWlanIDIndexedAPSpApId }
			::= { hwIDIndexedAPSpecificRadioTable 1 }
		HwIDIndexedAPSpecificRadioEntry ::=
			SEQUENCE {				
				hwIDIndexedAPSpRadio
					Unsigned32,
				hwIDIndexedAPSp5gRadioProfile
					OCTET STRING,
				hwIDIndexedAPSpMeshProfile
					OCTET STRING,
				hwIDIndexedAPSpWdsProfile
					OCTET STRING,
				hwIDIndexedAPSpLocationProfile
					OCTET STRING,
				hwIDIndexedAPSpRadio2gProfile
					OCTET STRING,
				hwIDIndexedAPSpMeshWhitelistProfile
					OCTET STRING,
				hwIDIndexedAPSpWdsWhitelistProfile
					OCTET STRING,
				hwIDIndexedAPSpRadioSwitch
					INTEGER,
				hwIDIndexedAPSpRadioChannel
					Unsigned32,
				hwIDIndexedAPSpRadioBandwidth
					INTEGER,
				hwIDIndexedAPSpRadioEirp
					Unsigned32,
				hwIDIndexedAPSpRadioAntennaGain
					Unsigned32,
				hwIDIndexedAPSpRadioCoverageDistance
					Unsigned32,
				hwIDIndexedAPSpRadioWorkMode
					INTEGER,
				hwIDIndexedAPSpRadioFrequency
					INTEGER,
				hwIDIndexedAPSpSpectrumAnalysisSwitch
					INTEGER,
				hwIDIndexedAPSpWidsDeviceDetectSwitch
					INTEGER,
				hwIDIndexedAPSpWidsAttackDetectEnBmp
					Unsigned32,
				hwIDIndexedAPSpWidsRogueContainSwitch
					INTEGER,
				hwIDIndexedAPSpRadioRowStatus
					RowStatus
			 }
		 --1.3.6.1.4.1.2011.6.139.11.1.71.1.1
		hwIDIndexedAPSpRadio OBJECT-TYPE
			SYNTAX Unsigned32 (0..2)
			MAX-ACCESS not-accessible
			STATUS current
			DESCRIPTION 
				"This object indicates the radio ID. It is the index of the table."
			::= { hwIDIndexedAPSpecificRadioEntry 1 }
		 --1.3.6.1.4.1.2011.6.139.11.1.71.1.2
		hwIDIndexedAPSp5gRadioProfile OBJECT-TYPE
			SYNTAX OCTET STRING (SIZE (0..35))
			MAX-ACCESS read-write
			STATUS current
			DESCRIPTION 
				"This object indicates the bound 5G radio profile."
			::= { hwIDIndexedAPSpecificRadioEntry 2 }
		 --1.3.6.1.4.1.2011.6.139.11.1.71.1.3
		hwIDIndexedAPSpMeshProfile OBJECT-TYPE
			SYNTAX OCTET STRING (SIZE (0..35))
			MAX-ACCESS read-write
			STATUS current
			DESCRIPTION 
				"This object indicates the bound Mesh profile."
			::= { hwIDIndexedAPSpecificRadioEntry 3 }
		 --1.3.6.1.4.1.2011.6.139.11.1.71.1.4
		hwIDIndexedAPSpWdsProfile OBJECT-TYPE
			SYNTAX OCTET STRING (SIZE (0..35))
			MAX-ACCESS read-write
			STATUS current
			DESCRIPTION 
				"This object indicates the bound WDS profile."
			::= { hwIDIndexedAPSpecificRadioEntry 4 }
	 --1.3.6.1.4.1.2011.6.139.11.1.71.1.5
		hwIDIndexedAPSpLocationProfile OBJECT-TYPE
			SYNTAX OCTET STRING (SIZE (0..35))
			MAX-ACCESS read-write
			STATUS current
			DESCRIPTION 
				"This object indicates the bound location profile."
			::= { hwIDIndexedAPSpecificRadioEntry 5 }
		-- 1.3.6.1.4.1.2011.6.139.11.1.71.1.6
		hwIDIndexedAPSpRadio2gProfile OBJECT-TYPE
			SYNTAX OCTET STRING (SIZE (0..35))
			MAX-ACCESS read-write
			STATUS current
			DESCRIPTION
				"This object indicates the system profile to which AP groups are bound. The default value is default."
			::= { hwIDIndexedAPSpecificRadioEntry 6 }
		-- 1.3.6.1.4.1.2011.6.139.11.1.71.1.7
		hwIDIndexedAPSpMeshWhitelistProfile OBJECT-TYPE
			SYNTAX OCTET STRING (SIZE (0..35))
			MAX-ACCESS read-write
			STATUS current
			DESCRIPTION
				"This object indicates the bound whitelist profile."
			::= { hwIDIndexedAPSpecificRadioEntry 7 }
		-- 1.3.6.1.4.1.2011.6.139.11.1.71.1.8
		hwIDIndexedAPSpWdsWhitelistProfile OBJECT-TYPE
			SYNTAX OCTET STRING (SIZE (0..35))
			MAX-ACCESS read-write
			STATUS current
			DESCRIPTION
				"This object indicates the bound whitelist profile."
			::= { hwIDIndexedAPSpecificRadioEntry 8 }
		-- 1.3.6.1.4.1.2011.6.139.11.1.71.1.9
		hwIDIndexedAPSpRadioSwitch OBJECT-TYPE
			SYNTAX INTEGER
				{
				disable(1),
				invalid(255)
				}
			MAX-ACCESS read-write
			STATUS current
			DESCRIPTION
				"This object indicates the name of a 2G radio profile. It is the index of the table."
			::= { hwIDIndexedAPSpecificRadioEntry 9 }
		-- 1.3.6.1.4.1.2011.6.139.11.1.71.1.10
		hwIDIndexedAPSpRadioChannel OBJECT-TYPE
			SYNTAX Unsigned32
			MAX-ACCESS read-write
			STATUS current
			DESCRIPTION
				"This object indicates a radio-frequency channel. For 2.4G, the value ranges from 1 to 13. For 5G, the value ranges from 36 to 165 (with a separation interval of 4)."
			::= { hwIDIndexedAPSpecificRadioEntry 10 }
		-- 1.3.6.1.4.1.2011.6.139.11.1.71.1.11
		hwIDIndexedAPSpRadioBandwidth OBJECT-TYPE
			SYNTAX INTEGER
				{
				ht20(1),
				ht40Plus(2),
				ht40Minus(3),
				ht80(4),
				invalid(255)
				}
			MAX-ACCESS read-write
			STATUS current
			DESCRIPTION
				"This object indicate a bandwidth. The default value is 1."
			::= { hwIDIndexedAPSpecificRadioEntry 11 }
		-- 1.3.6.1.4.1.2011.6.139.11.1.71.1.12
		hwIDIndexedAPSpRadioEirp OBJECT-TYPE
			SYNTAX Unsigned32 (1..127 | 255)
			MAX-ACCESS read-write
			STATUS current
			DESCRIPTION
				"This object indicates a power value. The default value is 127. The configuration is saved but the actual power is determined by the maximum power supported by the AP."
			::= { hwIDIndexedAPSpecificRadioEntry 12 }
		-- 1.3.6.1.4.1.2011.6.139.11.1.71.1.13
		hwIDIndexedAPSpRadioAntennaGain OBJECT-TYPE
			SYNTAX Unsigned32 (0..30 | 255)
			MAX-ACCESS read-write
			STATUS current
			DESCRIPTION
				"This object indicates antenna gains. The default value 0xFF indicates that the default gain of an AP is used. It is expressed in dB. Default gains vary with different types of APs."
			::= { hwIDIndexedAPSpecificRadioEntry 13 }
		-- 1.3.6.1.4.1.2011.6.139.11.1.71.1.14
		hwIDIndexedAPSpRadioCoverageDistance OBJECT-TYPE
			SYNTAX Unsigned32 (1..400 | 65535)
			MAX-ACCESS read-write
			STATUS current
			DESCRIPTION
				"This object indicates a radio coverage distance. The default value is 3. The unit is 0.1 km."
			::= { hwIDIndexedAPSpecificRadioEntry 14 }
		-- 1.3.6.1.4.1.2011.6.139.11.1.71.1.15
		hwIDIndexedAPSpRadioWorkMode OBJECT-TYPE
			SYNTAX INTEGER
				{
				normal(1),
				monitor(2),
				invalid(255)
				}
			MAX-ACCESS read-write
			STATUS current
			DESCRIPTION
				"This object indicates the radio working mode. The default value is 1."
			::= { hwIDIndexedAPSpecificRadioEntry 15 }
		-- 1.3.6.1.4.1.2011.6.139.11.1.71.1.16
		hwIDIndexedAPSpRadioFrequency OBJECT-TYPE
			SYNTAX INTEGER
				{
				frequency2G(1),
				frequency5G(2),
				invalid(255)
				}
			MAX-ACCESS read-write
			STATUS current
			DESCRIPTION
				"This object indicates the setting of the frequency band for radio 0. The default value is 1 ?	1: frequency2G ?	2: frequency5G."
			::= { hwIDIndexedAPSpecificRadioEntry 16 }
		-- 1.3.6.1.4.1.2011.6.139.11.1.71.1.17
		hwIDIndexedAPSpSpectrumAnalysisSwitch OBJECT-TYPE
			SYNTAX INTEGER
				{
				enable(2),
				invalid(255)
				}
			MAX-ACCESS read-write
			STATUS current
			DESCRIPTION
				"This object indicates the status of the spectrum analysis function. The default value is 1."
			::= { hwIDIndexedAPSpecificRadioEntry 17 }
		-- 1.3.6.1.4.1.2011.6.139.11.1.71.1.18
		hwIDIndexedAPSpWidsDeviceDetectSwitch OBJECT-TYPE
			SYNTAX INTEGER
				{
				enable(2),
				invalid(255)
				}
			MAX-ACCESS read-write
			STATUS current
			DESCRIPTION
				"This object indicates the status of the device detection function. The default value is 1."
			::= { hwIDIndexedAPSpecificRadioEntry 18 }
		-- 1.3.6.1.4.1.2011.6.139.11.1.71.1.19
		hwIDIndexedAPSpWidsAttackDetectEnBmp OBJECT-TYPE
			SYNTAX Unsigned32
			MAX-ACCESS read-write
			STATUS current
			DESCRIPTION
				"This object indicates the bit map of the brute force attack switch. bit0:weak-iv, bit1:spoof, bit2:flood, bit3:wpa-psk, bit4:wpa2-psk, bit5:wapi-psk, bit6:wep-psk."
			::= { hwIDIndexedAPSpecificRadioEntry 19 }
		-- 1.3.6.1.4.1.2011.6.139.11.1.71.1.20
		hwIDIndexedAPSpWidsRogueContainSwitch OBJECT-TYPE
			SYNTAX INTEGER
				{
				enable(2),
				invalid(255)
				}
			MAX-ACCESS read-write
			STATUS current
			DESCRIPTION
				"This object indicates the status of the device detection function. The default value is 1."
			::= { hwIDIndexedAPSpecificRadioEntry 20 }
		-- 1.3.6.1.4.1.2011.6.139.11.1.71.1.21
		hwIDIndexedAPSpRadioRowStatus OBJECT-TYPE
			SYNTAX RowStatus
			MAX-ACCESS read-write
			STATUS current
			DESCRIPTION 
				"This object indicates the row status of this table. ROWSTATUS_CREATEANDFLOW and ROWSTATUS_DESTROY are commonly used."
			::= { hwIDIndexedAPSpecificRadioEntry 21 }
		-- 1.3.6.1.4.1.2011.6.139.11.1.72
		hwIDIndexedAPSpecificVapTable OBJECT-TYPE
			SYNTAX SEQUENCE OF HwIDIndexedAPSpecificVapEntry 
			MAX-ACCESS not-accessible
			STATUS current
			DESCRIPTION 
				"This table is used to create VAPs in an AP specific profile."
			::= { hwWlanConfigObjects 72 }
		--1.3.6.1.4.1.2011.6.139.11.1.72.1
		hwIDIndexedAPSpecificVapEntry OBJECT-TYPE
			SYNTAX HwIDIndexedAPSpecificVapEntry 
			MAX-ACCESS not-accessible
			STATUS current
			DESCRIPTION 
				"Indexes of this table are hwIDIndexedAPSpWlan, hwIDIndexedAPSpRadio, and hwWlanIDIndexedAPSpApId."
			INDEX { hwIDIndexedAPSpWlan, hwIDIndexedAPSpRadio, hwWlanIDIndexedAPSpApId}
			::= { hwIDIndexedAPSpecificVapTable 1 }
		HwIDIndexedAPSpecificVapEntry ::=
			SEQUENCE {				
				hwIDIndexedAPSpWlan
					Unsigned32,
				hwIDIndexedAPSpVapProfile
					OCTET STRING,
				hwIDIndexedAPSpVapRowStatus
					RowStatus
			 }
		 --1.3.6.1.4.1.2011.6.139.11.1.72.1.1
		hwIDIndexedAPSpWlan OBJECT-TYPE
			SYNTAX Unsigned32 (1..16)
			MAX-ACCESS not-accessible
			STATUS current
			DESCRIPTION 
				"This object indicates the WLAN ID. It is the index of the table."
			::= { hwIDIndexedAPSpecificVapEntry 1 }
		 --1.3.6.1.4.1.2011.6.139.11.1.72.1.2
		hwIDIndexedAPSpVapProfile OBJECT-TYPE
			SYNTAX OCTET STRING (SIZE (1..35))
			MAX-ACCESS read-write
			STATUS current
			DESCRIPTION 
				"This object indicates the bound VAP profile."
			::= { hwIDIndexedAPSpecificVapEntry 2 }
		 --1.3.6.1.4.1.2011.6.139.11.1.72.1.3
		hwIDIndexedAPSpVapRowStatus OBJECT-TYPE
			SYNTAX RowStatus
			MAX-ACCESS read-write
			STATUS current
			DESCRIPTION 
				"This object indicates the row status of this table. createAndGo(4) and destroy(6) are commonly used."
			::= { hwIDIndexedAPSpecificVapEntry 3 }

		-- 1.3.6.1.4.1.2011.6.139.11.1.73
		hwBleProfileTable OBJECT-TYPE
			SYNTAX SEQUENCE OF HwBleProfileEntry
			MAX-ACCESS not-accessible
			STATUS current
			DESCRIPTION
				"Description."
			::= { hwWlanConfigObjects 73 }
			
		-- 1.3.6.1.4.1.2011.6.139.11.1.73.1
		hwBleProfileEntry OBJECT-TYPE
			SYNTAX HwBleProfileEntry
			MAX-ACCESS not-accessible
			STATUS current
			DESCRIPTION
				"Description."
			INDEX { hwWlanBLEProfileName }
			::= { hwBleProfileTable 1 }

		HwBleProfileEntry ::=
			SEQUENCE { 
				hwWlanBLEProfileName
					OCTET STRING,
				hwWlanBLEBroadcasterEnable
					INTEGER,
				hwWlanBLETxPower
					Integer32,
				hwWlanBLEBroadcastingUUID
					OCTET STRING,
				hwWlanBLEBroadcastingMajor
					OCTET STRING,
				hwWlanBLEBroadcastingMinor
					OCTET STRING,
				hwWlanBLEBroadcastingReferenceRSSI
					Integer32,
				hwWlanBLEBroadcastingInterval
					Unsigned32,
				hwWlanBLESnifferEnable
					INTEGER,
				hwWlanBLEProfileRowStatus
					RowStatus
			 }

		-- 1.3.6.1.4.1.2011.6.139.11.1.73.1.1
		hwWlanBLEProfileName OBJECT-TYPE
			SYNTAX OCTET STRING (SIZE (1..35))
			MAX-ACCESS not-accessible
			STATUS current
			DESCRIPTION
				"Description."
			::= { hwBleProfileEntry 1 }

		-- 1.3.6.1.4.1.2011.6.139.11.1.73.1.2
		hwWlanBLEBroadcasterEnable OBJECT-TYPE
			SYNTAX INTEGER
				{
				disable(1),
				enable(2)
				}
			MAX-ACCESS read-write
			STATUS current
			DESCRIPTION
				"Description."
			DEFVAL { disable }
			::= { hwBleProfileEntry 2 }

		-- 1.3.6.1.4.1.2011.6.139.11.1.73.1.3
		hwWlanBLETxPower OBJECT-TYPE
			SYNTAX Integer32
			UNITS "dbm"
			MAX-ACCESS read-write
			STATUS current
			DESCRIPTION
				"Description."
			DEFVAL { 0 }
			::= { hwBleProfileEntry 3 }

		-- 1.3.6.1.4.1.2011.6.139.11.1.73.1.4
		hwWlanBLEBroadcastingUUID OBJECT-TYPE
			SYNTAX OCTET STRING (SIZE (0..16))
			MAX-ACCESS read-write
			STATUS current
			DESCRIPTION
				"Description."
			::= { hwBleProfileEntry 4 }

		-- 1.3.6.1.4.1.2011.6.139.11.1.73.1.5
		hwWlanBLEBroadcastingMajor OBJECT-TYPE
			SYNTAX OCTET STRING (SIZE (0..2))
			MAX-ACCESS read-write
			STATUS current
			DESCRIPTION
				"Description."
			::= { hwBleProfileEntry 5 }

		-- 1.3.6.1.4.1.2011.6.139.11.1.73.1.6
		hwWlanBLEBroadcastingMinor OBJECT-TYPE
			SYNTAX OCTET STRING (SIZE (0..2))
			MAX-ACCESS read-write
			STATUS current
			DESCRIPTION
				"Description."
			::= { hwBleProfileEntry 6 }

		-- 1.3.6.1.4.1.2011.6.139.11.1.73.1.7
		hwWlanBLEBroadcastingReferenceRSSI OBJECT-TYPE
			SYNTAX Integer32 (-97..-50 | 0)
			UNITS "dbm"
			MAX-ACCESS read-write
			STATUS current
			DESCRIPTION
				"Description."
			DEFVAL { -65 }
			::= { hwBleProfileEntry 7 }

		-- 1.3.6.1.4.1.2011.6.139.11.1.73.1.8
		hwWlanBLEBroadcastingInterval OBJECT-TYPE
			SYNTAX Unsigned32 (100..10240)
			UNITS "ms"
			MAX-ACCESS read-write
			STATUS current
			DESCRIPTION
				"Description."
			DEFVAL { 500 }
			::= { hwBleProfileEntry 8 }

		-- 1.3.6.1.4.1.2011.6.139.11.1.73.1.9
		hwWlanBLESnifferEnable OBJECT-TYPE
			SYNTAX INTEGER
				{
				disable(1),
				enable(2)
				}
			MAX-ACCESS read-write
			STATUS current
			DESCRIPTION
				"Description."
			DEFVAL { disable }
			::= { hwBleProfileEntry 9 }

		-- 1.3.6.1.4.1.2011.6.139.11.1.73.1.10
		hwWlanBLEProfileRowStatus OBJECT-TYPE
			SYNTAX RowStatus
			MAX-ACCESS read-write
			STATUS current
			DESCRIPTION
				"Description."
			::= { hwBleProfileEntry 10 }

		-- 1.3.6.1.4.1.2011.6.139.11.1.74
		hwAPGroupCardTable OBJECT-TYPE
			SYNTAX SEQUENCE OF HwAPGroupCardEntry
			MAX-ACCESS not-accessible
			STATUS current
			DESCRIPTION
				"Description."
			::= { hwWlanConfigObjects 74 }

		-- 1.3.6.1.4.1.2011.6.139.11.1.74.1
		hwAPGroupCardEntry OBJECT-TYPE
			SYNTAX HwAPGroupCardEntry
			MAX-ACCESS not-accessible
			STATUS current
			DESCRIPTION
				"Description."
			INDEX { hwAPGrpCardIndex, hwAPGroupName }
			::= { hwAPGroupCardTable 1 }

		
		HwAPGroupCardEntry ::=
			SEQUENCE { 
				hwAPGrpCardIndex
					Unsigned32,
				hwAPGrpCardSerialProfile
					OCTET STRING,
				hwAPGrpCardProfile
					OCTET STRING,
				hwAPGrpCardNetUDPPort
					Unsigned32,
				hwAPGrpIoTRowStatus
					RowStatus
			 }

		-- 1.3.6.1.4.1.2011.6.139.11.1.74.1.1
		hwAPGrpCardIndex OBJECT-TYPE
			SYNTAX Unsigned32 (0..2)
			MAX-ACCESS not-accessible
			STATUS current
			DESCRIPTION
				"Description."
			::= { hwAPGroupCardEntry 1 }

		-- 1.3.6.1.4.1.2011.6.139.11.1.74.1.2
		hwAPGrpCardSerialProfile OBJECT-TYPE
			SYNTAX OCTET STRING (SIZE (1..35))
			MAX-ACCESS read-write
			STATUS current
			DESCRIPTION
				"Description."
			::= { hwAPGroupCardEntry 2 }

		-- 1.3.6.1.4.1.2011.6.139.11.1.74.1.3
		hwAPGrpCardProfile OBJECT-TYPE
			SYNTAX OCTET STRING (SIZE (0..35))
			MAX-ACCESS read-write
			STATUS current
			DESCRIPTION
				"Description."
			::= { hwAPGroupCardEntry 3 }

		-- 1.3.6.1.4.1.2011.6.139.11.1.74.1.4
		hwAPGrpCardNetUDPPort OBJECT-TYPE
			SYNTAX Unsigned32 (1025..55535)
			MAX-ACCESS read-write
			STATUS current
			DESCRIPTION
				"Description."
			::= { hwAPGroupCardEntry 4 }

		-- 1.3.6.1.4.1.2011.6.139.11.1.74.1.5
		hwAPGrpIoTRowStatus OBJECT-TYPE
			SYNTAX RowStatus
			MAX-ACCESS read-write
			STATUS current
			DESCRIPTION
				"Description."
			::= { hwAPGroupCardEntry 5 }

		-- 1.3.6.1.4.1.2011.6.139.11.1.75
		hwAPSpecificCardTable OBJECT-TYPE
			SYNTAX SEQUENCE OF HwAPSpecificCardEntry
			MAX-ACCESS not-accessible
			STATUS current
			DESCRIPTION
				"Description."
			::= { hwWlanConfigObjects 75 }

		-- 1.3.6.1.4.1.2011.6.139.11.1.75.1
		hwAPSpecificCardEntry OBJECT-TYPE
			SYNTAX HwAPSpecificCardEntry
			MAX-ACCESS not-accessible
			STATUS current
			DESCRIPTION
				"Description."
			INDEX { hwAPSpIoTIndex, hwAPSpApMac }
			::= { hwAPSpecificCardTable 1 }

		
		HwAPSpecificCardEntry ::=
			SEQUENCE { 
				hwAPSpIoTIndex
					Unsigned32,
				hwAPSpIoTSerialProfile
					OCTET STRING,
				hwAPSpIoTProfile
					OCTET STRING,
				hwAPSpIoTNetUDPPort
					Unsigned32,
				hwAPSpIoTRowStatus
					RowStatus
			 }

		-- 1.3.6.1.4.1.2011.6.139.11.1.75.1.1
		hwAPSpIoTIndex OBJECT-TYPE
			SYNTAX Unsigned32 (0..2)
			MAX-ACCESS not-accessible
			STATUS current
			DESCRIPTION
				"Description."
			::= { hwAPSpecificCardEntry 1 }

		-- 1.3.6.1.4.1.2011.6.139.11.1.75.1.2
		hwAPSpIoTSerialProfile OBJECT-TYPE
			SYNTAX OCTET STRING (SIZE (1..35))
			MAX-ACCESS read-write
			STATUS current
			DESCRIPTION
				"Description."
			::= { hwAPSpecificCardEntry 2 }

		-- 1.3.6.1.4.1.2011.6.139.11.1.75.1.3
		hwAPSpIoTProfile OBJECT-TYPE
			SYNTAX OCTET STRING (SIZE (0..35))
			MAX-ACCESS read-write
			STATUS current
			DESCRIPTION
				"Description."
			::= { hwAPSpecificCardEntry 3 }

		-- 1.3.6.1.4.1.2011.6.139.11.1.75.1.4
		hwAPSpIoTNetUDPPort OBJECT-TYPE
			SYNTAX Unsigned32 (1025..55535)
			MAX-ACCESS read-write
			STATUS current
			DESCRIPTION
				"Description."
			::= { hwAPSpecificCardEntry 4 }

		-- 1.3.6.1.4.1.2011.6.139.11.1.75.1.5
		hwAPSpIoTRowStatus OBJECT-TYPE
			SYNTAX RowStatus
			MAX-ACCESS read-write
			STATUS current
			DESCRIPTION
				"Description."
			::= { hwAPSpecificCardEntry 5 }

		-- 1.3.6.1.4.1.2011.6.139.11.1.76
		hwIoTSerialProfileTable OBJECT-TYPE
			SYNTAX SEQUENCE OF HwIoTSerialProfileEntry
			MAX-ACCESS not-accessible
			STATUS current
			DESCRIPTION
				"Description."
			::= { hwWlanConfigObjects 76 }

		-- 1.3.6.1.4.1.2011.6.139.11.1.76.1
		hwIoTSerialProfileEntry OBJECT-TYPE
			SYNTAX HwIoTSerialProfileEntry
			MAX-ACCESS not-accessible
			STATUS current
			DESCRIPTION
				"Description."
			INDEX { hwIoTSerialProfileName }
			::= { hwIoTSerialProfileTable 1 }

		
		HwIoTSerialProfileEntry ::=
			SEQUENCE { 
				hwIoTSerialProfileName
					OCTET STRING,
				hwIoTSerialSpeed
					Unsigned32,
				hwIoTSerialParity
					INTEGER,
				hwIoTSerialStopbits
					INTEGER,
				hwIoTSerialFrameFormat
					INTEGER,
				hwIoTSerialFrameLength
					Unsigned32,
				hwIoTSerialFrameStart
					Unsigned32,
				hwIoTSerialFrameStop
					Unsigned32,
				hwIoTSerialProfileRowStatus
					RowStatus
			 }

		-- 1.3.6.1.4.1.2011.6.139.11.1.76.1.1
		hwIoTSerialProfileName OBJECT-TYPE
			SYNTAX OCTET STRING (SIZE (1..35))
			MAX-ACCESS not-accessible
			STATUS current
			DESCRIPTION
				"Description."
			::= { hwIoTSerialProfileEntry 1 }

		-- 1.3.6.1.4.1.2011.6.139.11.1.76.1.2
		hwIoTSerialSpeed OBJECT-TYPE
			SYNTAX Unsigned32 (9600..115200)
			MAX-ACCESS read-write
			STATUS current
			DESCRIPTION
				"Description."
			::= { hwIoTSerialProfileEntry 2 }

		-- 1.3.6.1.4.1.2011.6.139.11.1.76.1.3
		hwIoTSerialParity OBJECT-TYPE
			SYNTAX INTEGER
				{
				none(1),
				odd(2),
				even(3),
				space(4),
				mark(5)
				}
			MAX-ACCESS read-write
			STATUS current
			DESCRIPTION
				"Description."
			DEFVAL { none }
			::= { hwIoTSerialProfileEntry 3 }

		-- 1.3.6.1.4.1.2011.6.139.11.1.76.1.4
		hwIoTSerialStopbits OBJECT-TYPE
			SYNTAX INTEGER
				{
				zero(1),
				oneHalf(2),
				two(3)
				}
			MAX-ACCESS read-write
			STATUS current
			DESCRIPTION
				"Description."
			DEFVAL { zero }
			::= { hwIoTSerialProfileEntry 4 }

		-- 1.3.6.1.4.1.2011.6.139.11.1.76.1.5
		hwIoTSerialFrameFormat OBJECT-TYPE
			SYNTAX INTEGER
				{
				fixedLength(1),
				frameBeginEnd(2)
				}
			MAX-ACCESS read-write
			STATUS current
			DESCRIPTION
				"Description."
			DEFVAL { frame-begin-end }
			::= { hwIoTSerialProfileEntry 5 }

		-- 1.3.6.1.4.1.2011.6.139.11.1.76.1.6
		hwIoTSerialFrameLength OBJECT-TYPE
			SYNTAX Unsigned32 (1..280)
			MAX-ACCESS read-write
			STATUS current
			DESCRIPTION
				"Description."
			DEFVAL { 265 }
			::= { hwIoTSerialProfileEntry 6 }

		-- 1.3.6.1.4.1.2011.6.139.11.1.76.1.7
		hwIoTSerialFrameStart OBJECT-TYPE
			SYNTAX Unsigned32 (0..255)
			MAX-ACCESS read-write
			STATUS current
			DESCRIPTION
				"Description."
			DEFVAL { 'aa'h }
			::= { hwIoTSerialProfileEntry 7 }

		-- 1.3.6.1.4.1.2011.6.139.11.1.76.1.8
		hwIoTSerialFrameStop OBJECT-TYPE
			SYNTAX Unsigned32 (0..255)
			MAX-ACCESS read-write
			STATUS current
			DESCRIPTION
				"Description."
			DEFVAL { '7e'h }
			::= { hwIoTSerialProfileEntry 8 }

		-- 1.3.6.1.4.1.2011.6.139.11.1.76.1.9
		hwIoTSerialProfileRowStatus OBJECT-TYPE
			SYNTAX RowStatus
			MAX-ACCESS read-write
			STATUS current
			DESCRIPTION
				"Description."
			::= { hwIoTSerialProfileEntry 9 }

		-- 1.3.6.1.4.1.2011.6.139.11.1.77
		hwIoTProfileTable OBJECT-TYPE
			SYNTAX SEQUENCE OF HwIoTProfileEntry
			MAX-ACCESS not-accessible
			STATUS current
			DESCRIPTION
				"Description."
			::= { hwWlanConfigObjects 77 }

		-- 1.3.6.1.4.1.2011.6.139.11.1.77.1
		hwIoTProfileEntry OBJECT-TYPE
			SYNTAX HwIoTProfileEntry
			MAX-ACCESS not-accessible
			STATUS current
			DESCRIPTION
				"Description."
			INDEX { hwIoTProfileName }
			::= { hwIoTProfileTable 1 }

		
		HwIoTProfileEntry ::=
			SEQUENCE { 
				hwIoTProfileName
					OCTET STRING,
				hwIoTProfileConfigAgentPermitIp
					IpAddress,
				hwIoTProfileConfigAgentPermitMaskLen
					Unsigned32,
				hwIoTProfileShareKey
					OCTET STRING,
				hwIoTProfileRowStatus
					RowStatus
			 }

		-- 1.3.6.1.4.1.2011.6.139.11.1.77.1.1
		hwIoTProfileName OBJECT-TYPE
			SYNTAX OCTET STRING (SIZE (1..35))
			MAX-ACCESS not-accessible
			STATUS current
			DESCRIPTION
				"Description."
			::= { hwIoTProfileEntry 1 }

		-- 1.3.6.1.4.1.2011.6.139.11.1.77.1.2
		hwIoTProfileConfigAgentPermitIp OBJECT-TYPE
			SYNTAX IpAddress
			MAX-ACCESS read-write
			STATUS current
			DESCRIPTION
				"Description."
			::= { hwIoTProfileEntry 2 }

		-- 1.3.6.1.4.1.2011.6.139.11.1.77.1.3
		hwIoTProfileConfigAgentPermitMaskLen OBJECT-TYPE
			SYNTAX Unsigned32 (0..32)
			MAX-ACCESS read-write
			STATUS current
			DESCRIPTION
				"Description."
			::= { hwIoTProfileEntry 3 }

		-- 1.3.6.1.4.1.2011.6.139.11.1.77.1.4
		hwIoTProfileShareKey OBJECT-TYPE
			SYNTAX OCTET STRING (SIZE (1..68))
			MAX-ACCESS read-write
			STATUS current
			DESCRIPTION
				"Description."
			::= { hwIoTProfileEntry 4 }

		-- 1.3.6.1.4.1.2011.6.139.11.1.77.1.5
		hwIoTProfileRowStatus OBJECT-TYPE
			SYNTAX RowStatus
			MAX-ACCESS read-write
			STATUS current
			DESCRIPTION
				"Description."
			::= { hwIoTProfileEntry 5 }

		-- 1.3.6.1.4.1.2011.6.139.11.1.78
		hwIoTProfileManagementServerTable OBJECT-TYPE
			SYNTAX SEQUENCE OF HwIoTProfileManagementServerEntry
			MAX-ACCESS not-accessible
			STATUS current
			DESCRIPTION
				"Description."
			::= { hwWlanConfigObjects 78 }


		-- 1.3.6.1.4.1.2011.6.139.11.1.78.1
		hwIoTProfileManagementServerEntry OBJECT-TYPE
			SYNTAX HwIoTProfileManagementServerEntry
			MAX-ACCESS not-accessible
			STATUS current
			DESCRIPTION
				"Description."
			INDEX { hwIoTProfileName, hwIoTProfileManagementServerIndex }
			::= { hwIoTProfileManagementServerTable 1 }

		
		HwIoTProfileManagementServerEntry ::=
			SEQUENCE { 
				hwIoTProfileManagementServerIndex
					Unsigned32,
				hwIoTProfileManagementServerIp
					IpAddress,
				hwIoTProfileManagementServerPort
					Unsigned32,
				hwIoTProfileManagementServerRowStatus
					RowStatus
			 }

		-- 1.3.6.1.4.1.2011.6.139.11.1.78.1.1
		hwIoTProfileManagementServerIndex OBJECT-TYPE
			SYNTAX Unsigned32 (0..3)
			MAX-ACCESS not-accessible
			STATUS current
			DESCRIPTION
				"Description."
			::= { hwIoTProfileManagementServerEntry 1 }

		-- 1.3.6.1.4.1.2011.6.139.11.1.78.1.2
		hwIoTProfileManagementServerIp OBJECT-TYPE
			SYNTAX IpAddress
			MAX-ACCESS read-write
			STATUS current
			DESCRIPTION
				"Description."
			::= { hwIoTProfileManagementServerEntry 2 }

		-- 1.3.6.1.4.1.2011.6.139.11.1.78.1.3
		hwIoTProfileManagementServerPort OBJECT-TYPE
			SYNTAX Unsigned32 (1025..55535)
			MAX-ACCESS read-write
			STATUS current
			DESCRIPTION
				"Description."
			::= { hwIoTProfileManagementServerEntry 3 }

		-- 1.3.6.1.4.1.2011.6.139.11.1.78.1.4
		hwIoTProfileManagementServerRowStatus OBJECT-TYPE
			SYNTAX RowStatus
			MAX-ACCESS read-write
			STATUS current
			DESCRIPTION
				"Description."
			::= { hwIoTProfileManagementServerEntry 4 }
			
		--1.3.6.1.4.1.2011.6.139.11.2
		hwWlanConfigConformance OBJECT IDENTIFIER ::= { hwWlanConfig 2 }

		--1.3.6.1.4.1.2011.6.139.11.2.1
		hwWlanConfigCompliances OBJECT IDENTIFIER ::= { hwWlanConfigConformance 1 }

		--1.3.6.1.4.1.2011.6.139.11.2.1.1
		hwWlanConfigCompliance MODULE-COMPLIANCE
			STATUS current
			DESCRIPTION 
				"Description."
			MODULE -- this module
				MANDATORY-GROUPS { hwWlanGlobalConfigGroups, hwApAuthObjectsGroups, hwAPGroupGroups, hwAPGroupWiredPortGroups, hwAPGroupRadioGroups, 
					hwAPGroupVapGroups, hwAPSpecificGroups, hwAPSpecificWiredPortGroups, hwAPSpecificRadioGroups, hwAPSpecificVapGroups, 
					hwRegulatoryDomainProfileGroups, hwApSystemProfileGroups, hwAPWiredPortProfileGroups, hwAPPortLinkProfileGroups, hw2gRadioProfileGroups, 
					hw5gRadioProfileGroups, hwRrmProfileGroups, hwAirScanProfileGroups, hwVapProfileGroups, hwSsidProfileGroups, 
					hwSecurityProfileGroups, hwAPTrafficProfileGroups, hwWlanVlanPoolGroups, hwStaWhitelistProfileGroups, hwStaBlacklistProfileGroups, 
					hwWidsProfileGroups, hwWidsSpoofProfileGroups, 
					hwWidsWhitelistProfileGroups, hwMeshProfileGroups, hwMeshWhitelistProfileGroups, hwMeshHandoverProfileGroups, hwWdsProfileGroups, 
					hwWdsWhitelistProfileGroups, hwHotspot2ProfileGroups, hwCellularNetworkProfileGroups, 
					hwConnectionCapabilityProfileGroups, hwOperatorNameProfileGroups, hwOperatorClassProfileGroups, hwOperatorDomainNameProfileGroups, hwNAIRealmProfileGroups, 
					hwVenueNameProfileGroups, hwRoamingConsortiumProfileGroups, hwSACProfileGroups, hwSACProfActionGroups, hwAPProvisionGroups, 
					hwWlanRadioCalibrateManagementGroups, hwWlanMobilityGroups, hwWlanLanguageGroups, hwFatApConfigGroups, hwWidsSpoofProfileListGroups, 
					hwWidsWhitelistProfileListGroups, hwWlanLoadBalanceStaticGroupGroups, hwWlanLoadBalanceStaticGroupMemberGroups, hwWlanCountryCodeGroups, hwUccProfileGroups, 
					hwSoftgreProfileGroups }
			::= { hwWlanConfigCompliances 1 }

		--1.3.6.1.4.1.2011.6.139.11.2.2
		hwWlanConfigObjectGroups OBJECT IDENTIFIER ::= { hwWlanConfigConformance 2 }

		
		-- 1.3.6.1.4.1.2011.6.139.11.2.2.1
		hwWlanGlobalConfigGroups OBJECT-GROUP
			OBJECTS { hwWlanGlobalApUsername, hwWlanGlobalApPassword, hwWlanUsernamePasswordApMac, hwWlanGlobalApLldpSwitch, hwWlanGlobalIpv6Enable, 
				hwWlanStationIpv6Enable, hwWlanApDataCollectionInterval, hwTestRtCollectOnoff, hwTestApNormalCollectCycle, hwTestApRtCollectCycle, 
				hwWlanConfigCommitAll, hwWlanProtectIpAddress, hwWlanProtectIPv6Address, hwWlanProtectPriority, hwWlanProtectSwitch, 
				hwWlanProtectRestoreSwitch, hwUndoWlanProtectIpAddress, hwUndoWlanProtectPriority, hwWlanCfgHsbServiceType, hwWlanCfgHsbGroupId, 
				hwWlanCfgHsbTunnelId, hwWlanConfigCommit, hwWlanReportStaInfo}
			STATUS current
			DESCRIPTION 
				"Description."
			::= { hwWlanConfigObjectGroups 1 }

		
		-- 1.3.6.1.4.1.2011.6.139.11.2.2.2
		hwApAuthObjectsGroups OBJECT-GROUP
			OBJECTS { hwWlanApAuthMode, hwWlanApMacWhitelistRowStatus, hwWlanApSnWhitelistRowStatus, hwWlanApMacBlacklistRowStatus }
			STATUS current
			DESCRIPTION 
				"Description."
			::= { hwWlanConfigObjectGroups 2 }


		-- 1.3.6.1.4.1.2011.6.139.11.2.2.3
		hwAPGroupGroups OBJECT-GROUP
			OBJECTS { hwAPGrpAPSystemProfile, hwAPGrpDomainProfile, hwAPGrpRowStatus, hwAPGrpWidsProfile }
			STATUS current
			DESCRIPTION 
				"Description."
			::= { hwWlanConfigObjectGroups 3 }


		-- 1.3.6.1.4.1.2011.6.139.11.2.2.4
		hwAPGroupWiredPortGroups OBJECT-GROUP
			OBJECTS {hwAPGrpWPProfile, hwAPGrpWPRowStatus }
			STATUS current
			DESCRIPTION 
				"Description."
			::= { hwWlanConfigObjectGroups 4 }


		-- 1.3.6.1.4.1.2011.6.139.11.2.2.5
		hwAPGroupRadioGroups OBJECT-GROUP
			OBJECTS { hwAPGrpRadio5gProfile, hwAPGrpMeshProfile, hwAPGrpWdsProfile, hwAPGrpLocationProfile, hwAPGrpRadioRowStatus, hwAPGrpRadio2gProfile, 
				hwAPGrpMeshWhitelistProfile, hwAPGrpWdsWhitelistProfile, hwAPGrpRadioSwitch, hwAPGrpRadioChannel, hwAPGrpRadioBandwidth, 
				hwAPGrpRadioEirp, hwAPGrpRadioAntennaGain, hwAPGrpRadioCoverageDistance, hwAPGrpRadioWorkMode, hwAPGrpRadioFrequency, 
				hwAPGrpSpectrumAnalysisSwitch, hwAPGrpWidsDeviceDetectSwitch, hwAPGrpWidsAttackDetectEnBmp, hwAPGrpWidsRogueContainSwitch,
				hwAPGrpRadioSecondChannel }
			STATUS current
			DESCRIPTION 
				"Description."
			::= { hwWlanConfigObjectGroups 5 }


		-- 1.3.6.1.4.1.2011.6.139.11.2.2.6
		hwAPGroupVapGroups OBJECT-GROUP
			OBJECTS {hwAPGrpVapProfile, hwAPGrpVapRowStatus }
			STATUS current
			DESCRIPTION 
				"Description."
			::= { hwWlanConfigObjectGroups 6 }


		-- 1.3.6.1.4.1.2011.6.139.11.2.2.7
		hwAPSpecificGroups OBJECT-GROUP
			OBJECTS { hwAPSpAPSystemProfile, hwAPSpDomainProfile, hwAPSpRowStatus, hwAPSpApId, hwAPSpApTypeInfo, hwAPSpWidsProfile
				 }
			STATUS current
			DESCRIPTION 
				"Description."
			::= { hwWlanConfigObjectGroups 7 }

			
		-- 1.3.6.1.4.1.2011.6.139.11.2.2.8
		hwAPSpecificWiredPortGroups OBJECT-GROUP
			OBJECTS { hwAPSpWPProfile, hwAPSpWPRowStatus, hwAPSpWPApId }
			STATUS current
			DESCRIPTION 
				"Description."
			::= { hwWlanConfigObjectGroups 8 }


		-- 1.3.6.1.4.1.2011.6.139.11.2.2.9
		hwAPSpecificRadioGroups OBJECT-GROUP
			OBJECTS { hwAPSp5gRadioProfile, hwAPSpMeshProfile, hwAPSpWdsProfile, hwAPSpLocationProfile, hwAPSpRadioRowStatus, hwAPSpRadio2gProfile, 
				hwAPSpMeshWhitelistProfile, hwAPSpWdsWhitelistProfile, hwAPSpRadioSwitch, hwAPSpRadioChannel, hwAPSpRadioBandwidth, 
				hwAPSpRadioEirp, hwAPSpRadioAntennaGain, hwAPSpRadioCoverageDistance, hwAPSpRadioWorkMode, hwAPSpRadioFrequency, 
				hwAPSpSpectrumAnalysisSwitch, hwAPSpWidsDeviceDetectSwitch, hwAPSpWidsAttackDetectEnBmp, hwAPSpWidsRogueContainSwitch, hwAPSpRadioApId,
				hwAPSpRadioSecondChannel }
			STATUS current
			DESCRIPTION 
				"Description."
			::= { hwWlanConfigObjectGroups 9 }


		-- 1.3.6.1.4.1.2011.6.139.11.2.2.10
		hwAPSpecificVapGroups OBJECT-GROUP
			OBJECTS { hwAPSpVapProfile, hwAPSpVapRowStatus, hwAPSpVapApId }
			STATUS current
			DESCRIPTION 
				"Description."
			::= { hwWlanConfigObjectGroups 10 }


		-- 1.3.6.1.4.1.2011.6.139.11.2.2.11
		hwRegulatoryDomainProfileGroups OBJECT-GROUP
			OBJECTS { hwCountryCode, hwDcaChannel5GBandwidth, hwDcaChannel5GChannelSet, hwDcaChannel2GChannelSet, hwRegulatoryDomainProfilRowStatus
				 }
			STATUS current
			DESCRIPTION 
				"Description."
			::= { hwWlanConfigObjectGroups 11 }


		-- 1.3.6.1.4.1.2011.6.139.11.2.2.12
		hwApSystemProfileGroups OBJECT-GROUP
			OBJECTS { hwApProfStatInterval, hwApProfSampleTime, hwApProfLedSwitch, hwApProfMaxStaNum, hwApProfMtu, 
				hwApProfMeshRole, hwApProfTemporaryManagement, hwApProfManagementVlan, hwApProfHighTempThreshold, hwApProfLowTempThreshold, 
				hwApProfOpHRxPowerThreshold, hwApProfOpLRxPowerThreshold, hwApProfOpHTempThreshold, hwApProfOpLTempThreshold, hwApProfMemoryUsageThreshold, 
				hwApProfCpuUsageThreshold, hwApProfTelnetSwitch, hwApProfSTelnetSwitch, hwApProfConsoleSwitch, hwApProfLogRecordLevel, 
				hwApProfLogServerIp, hwApProfLogServerIpv6, hwApProfAlarmRestrictionSwitch, hwApProfAlarmRestrictionPeriod, hwApProfKeepServiceSwitch, 
				hwApProfProtectPriority, hwApProfProtectACIp, hwApProfProtectACIpv6, hwApProfEapStartMode, hwApProfEapStartTransform, 
				hwApProfEapStartUnicastMac, hwApProfEapResponseMode, hwApProfEapResponseTransform, hwApProfEapResponseUnicastMac, hwApProfLldpRestartDelay, 
				hwApProfLldpAdminStatus, hwApProfLldpRetransDelay, hwApProfLldpRetransHoldMultiplier, hwApProfLldpInterval, hwApProfLldpReportInterval, 
				hwApProfStaAccessMode, hwApProfStaAccessModeProfile, hwApProfRowStatus, hwApProfSFTPSwitch, hwApProfDynamicBlackListAgingTime, 
				hwApProfAntennaOutputMode, hwApProfMppActiveReselectionSwitch, hwApProfSpectrumServerIPAddress, hwApProfSpectrumServerIPv6Address, hwApProfSpectrumServerPort, 
				hwApProfSpectrumViaACSwitch, hwApProfSpectrumViaACPort, hwApProfSpectrumNonWifiDeviceAgingTime, hwApProfPoeMaxPower, hwApProfPoePowerReserved,
				hwApProfPoePowerThreshold, hwApProfPoeAfInrushSwitch, hwApProfPoeHighInrushSwitch }
			STATUS current
			DESCRIPTION 
				"Description."
			::= { hwWlanConfigObjectGroups 12 }


		-- 1.3.6.1.4.1.2011.6.139.11.2.2.13
		hwAPWiredPortProfileGroups OBJECT-GROUP
			OBJECTS { hwAPWiredPortPortLinkProfileName, hwAPWiredPortProfilePortDesc, hwAPWiredPortProfilePortEthTrunkID, hwAPWiredPortProfilePortSTPSwitch, hwAPWiredPortProfilePortMode, 
				hwAPWiredPortProfilePortVlanPvid, hwAPWiredPortProfilePortVlanTagged, hwAPWiredPortProfilePortVlanUntagged, hwAPWiredPortProfileUserIsolate, hwAPWiredPortProfileDhcpTrust, 
				hwAPWiredPortProfileNdTrust, hwAPWiredPortProfileRowStatus, hwAPWiredPortProfileLearnAddress, hwAPWiredPortProfileIpBindCheck, hwAPWiredPortProfileArpBindCheck,
				hwAPWiredPortProfileSTPAutoShutdown, hwAPWiredPortProfileSTPAutoShutdownRecoveryTime, hwAPWiredPortProfileTrafficOptimizeSuppressionBc, hwAPWiredPortProfileTrafficOptimizeSuppressionUc, hwAPWiredPortProfileTrafficOptimizeSuppressionMc,
				hwAPWiredPortProfileTrafficFilterAclID, hwAPWiredPortProfileTrafficFilterRowStatus }
			STATUS current
			DESCRIPTION 
				"Description."
			::= { hwWlanConfigObjectGroups 13 }


		-- 1.3.6.1.4.1.2011.6.139.11.2.2.14
		hwAPPortLinkProfileGroups OBJECT-GROUP
			OBJECTS { hwAPPortLinkProfileLldpEnable, hwAPPortLinkProfileLldpTlvType, hwAPPortLinkProfileCrcAlarmEnable, hwAPPortLinkProfileCrcAlarmThreshold, hwAPPortLinkProfileCrcAlarmResumeThreshold, 
				hwAPPortLinkProfileRowStatus, hwAPPortLinkProfilePoeSwitch, hwAPPortLinkProfilePoePriority, hwAPPortLinkProfilePoeForcePowerSwitch, hwAPPortLinkProfilePoeLegacySwitch,
				hwAPPortLinkProfilePoeOffTimeRange, hwAPPortLinkProfileAdminStatus }
			STATUS current
			DESCRIPTION 
				"Description."
			::= { hwWlanConfigObjectGroups 14 }


		-- 1.3.6.1.4.1.2011.6.139.11.2.2.15
		hw2gRadioProfileGroups OBJECT-GROUP
			OBJECTS { hw2gRadioBeaconInterval, hw2gRadioGuardIntervalMode, hw2gRadioShortPreamble, hw2gRadioFragmentationThreshold, hw2gRadioHtAmpduSwitch, 
				hw2gRadioHtAmpduMaxLengthExponent, hw2gRadioDot11bgBasicRate, hw2gRadioDot11bgSupportRate, hw2gRadioMulticastRate, hw2gRadioWmmMandatorySwitch, 
				hw2gRadioApEDCAVoiceECWmax, hw2gRadioApEDCAVoiceECWmin, hw2gRadioApEDCAVoiceAIFSN, hw2gRadioApEDCAVoiceTXOPLimit, hw2gRadioApEDCAVoiceAckPolicy, 
				hw2gRadioApEDCAVideoECWmax, hw2gRadioApEDCAVideoECWmin, hw2gRadioApEDCAVideoAIFSN, hw2gRadioApEDCAVideoTXOPLimit, hw2gRadioApEDCAVideoAckPolicy, 
				hw2gRadioApEDCABEECWmax, hw2gRadioApEDCABEECWmin, hw2gRadioApEDCABEAIFSN, hw2gRadioApEDCABETXOPLimit, hw2gRadioApEDCABEAckPolicy, 
				hw2gRadioApEDCABKECWmax, hw2gRadioApEDCABKECWmin, hw2gRadioApEDCABKAIFSN, hw2gRadioApEDCABKTXOPLimit, hw2gRadioApEDCABKAckPolicy, 
				hw2gRadioWmmSwitch, hw2gRadioRtsCtsThreshold, hw2gRadioRtsCtsMode, hw2gRadioPowerAutoAdjustSwitch, hw2gRadioBeamformingSwitch, 
				hw2gRadioWifiLight, hw2gRadioChannelSwitchAnnouncementSwitch, hw2gRadioChannelSwitchMode, hw2gRadioAutoOffServiceSwitch, hw2gRadioAutoOffServiceStartTime, 
				hw2gRadioAutoOffServiceEndTime, hw2gRadioInterferenceDetectSwitch, hw2gRadioInterferenceIntraFrequencyThreshold, hw2gRadioInterferenceAdjacentFrequencyThreshold, hw2gRadioInterferenceStationThreshold, 
				hw2gRadioRrmProfile, hw2gRadioAirScanProfile, hw2gRadioProfileRowStatus, hw2gRadioProfileUtmostPowerSwitch, hw2gRadioProfileRadioType,
				hw2gRadioProfileSmartAntennaEnable, hw2gRadioProfileTxChainNum, hw2gRadioProfileRxChainNum }
			STATUS current
			DESCRIPTION 
				"Description."
			::= { hwWlanConfigObjectGroups 15 }


		-- 1.3.6.1.4.1.2011.6.139.11.2.2.16
		hw5gRadioProfileGroups OBJECT-GROUP
			OBJECTS { hw5gRadioBeaconInterval, hw5gRadioGuardIntervalMode, hw5gRadioShortPreamble, hw5gRadioFragmentationThreshold, hw5gRadioHtAmpduSwitch, 
				hw5gRadioHtAmpduMaxLengthExponent, hw5gRadioVhtAmpduMaxLengthExponent, hw5gRadioVhtAmsduSwitch, hw5gRadioVhtAmsduMaxFrameNum, hw5gRadioDot11aBasicRate, 
				hw5gRadioDot11aSupportRate, hw5gRadioMulticastRate, hw5gRadioVhtNssMapMaxMcs, hw5gRadioWmmMandatorySwitch, hw5gRadioApEDCAVoiceECWmax, 
				hw5gRadioApEDCAVoiceECWmin, hw5gRadioApEDCAVoiceAIFSN, hw5gRadioApEDCAVoiceTXOPLimit, hw5gRadioApEDCAVoiceAckPolicy, hw5gRadioApEDCAVideoECWmax, 
				hw5gRadioApEDCAVideoECWmin, hw5gRadioApEDCAVideoAIFSN, hw5gRadioApEDCAVideoTXOPLimit, hw5gRadioApEDCAVideoAckPolicy, hw5gRadioApEDCABEECWmax, 
				hw5gRadioApEDCABEECWmin, hw5gRadioApEDCABEAIFSN, hw5gRadioApEDCABETXOPLimit, hw5gRadioApEDCABEAckPolicy, hw5gRadioApEDCABKECWmax, 
				hw5gRadioApEDCABKECWmin, hw5gRadioApEDCABKAIFSN, hw5gRadioApEDCABKTXOPLimit, hw5gRadioApEDCABKAckPolicy, hw5gRadioWmmSwitch, 
				hw5gRadioRtsCtsThreshold, hw5gRadioRtsCtsMode, hw5gRadioPowerAutoAdjustSwitch, hw5gRadioBeamformingSwitch, hw5gRadioWifiLight, 
				hw5gRadioChannelSwitchAnnouncementSwitch, hw5gRadioChannelSwitchMode, hw5gRadioAutoOffServiceSwitch, hw5gRadioAutoOffServiceStartTime, hw5gRadioAutoOffServiceEndTime, 
				hw5gRadioInterferenceDetectSwitch, hw5gRadioInterferenceIntraFrequencyThreshold, hw5gRadioInterferenceAdjacentFrequencyThreshold, hw5gRadioInterferenceStationThreshold, hw5gRadioRrmProfile, 
				hw5gRadioAirScanProfile, hw5gRadioProfileRowStatus, hw5gRadioProfileUtmostPowerSwitch, hw5gRadioProfileRadioType, hw5gRadioProfileSmartAntennaEnable, hw5gRadioProfileMuMIMOEnable,
                                                                      hw5gRadioProfileTxChainNum, hw5gRadioProfileRxChainNum
				 }
			STATUS current
			DESCRIPTION 
				"Description."
			::= { hwWlanConfigObjectGroups 16 }


		-- 1.3.6.1.4.1.2011.6.139.11.2.2.17
		hwRrmProfileGroups OBJECT-GROUP
			OBJECTS { hwRrmAutoChannelSelectSwitch, hwRrmAutoTxPowerSelectSwitch, hwRrmErrRateThreshold, hwRrmAirtimeFairSchduleSwitch, hwRrmDynamicEdcaSwitch, 
				hwRrmUacLimitClientSnrSwitch, hwRrmUacClientSnrThreshold, hwRrmUacPolicySwitch, hwRrmUacPolicyType, hwRrmUacReachThresholdHideSsidSwitch, 
				hwRrmBandSteerDenyThreshold, hwRrmBandSteerLbClientThreshold, hwRrmBandSteerLbGapThreshold, hwRrmBandSteerClientBandsExpire, hwRrmLoadBalanceSwitch, 
				hwRrmLoadBalanceClientThreshold, hwRrmLoadBalanceGapThreshold, hwRrmLoadBalanceDenyThreshold, hwRrmSmartRoamCheckType, hwRrmSmartRoamSwitch, 
				hwRrmSmartRoamSnrThreshold, hwRrmSmartRoamRateThreshold, hwRrmSmartRoamSnrHighLevelMargin, hwRrmSmartRoamSnrLowLevelMargin, hwRrmSmartRoamSnrCheckInterval, 
				hwRrmSmartRoamUnableRoamExpireTime, hwRrmProfileRowStatus }
			STATUS current
			DESCRIPTION 
				"Description."
			::= { hwWlanConfigObjectGroups 17 }


		-- 1.3.6.1.4.1.2011.6.139.11.2.2.18
		hwAirScanProfileGroups OBJECT-GROUP
			OBJECTS { hwAirScanPeriod, hwAirScanInterval, hwAirScanChannelSet, hwAirScanProfilRowStatus, hwAirScanVoiceAware, 
				hwAirScanVideoAware }
			STATUS current
			DESCRIPTION 
				"Description."
			::= { hwWlanConfigObjectGroups 18 }


		-- 1.3.6.1.4.1.2011.6.139.11.2.2.19
		hwVapProfileGroups OBJECT-GROUP
			OBJECTS { hwVapForwardMode, hwVapTunnelForwardProtocol, hwVapServiceSwitch, hwVapAutoOffStartTime, hwVapAutoOffEndTime, 
				hwVapTemporaryManagementSwitch, hwVapServiceVlan, hwVapVlanPool, hwVapType, hwVapStaAccessMode, 
				hwVapStaAccessModePorfile, hwVapRoamHomeAgent, hwVapRoamVlanMobilityGroup, hwVapRoamLayer3Switch, hwVapBandSteerSwitch, 
				hwVapLearnIpv4Address, hwVapLearnIpv6Address, hwVapLearnIpv4AddressStrict, hwVapIpBindCheck, hwVapArpBindCheck, 
				hwVapOptinon82InsertSwitch, hwVapOptinon82InsertRidFormat, hwVapDhcpTrustPort, hwVapNdTrustPort, hwVapSecurityProfile, 
				hwVapTrafficProfile, hwVapSsidProfile, hwVapAuthenticationProfile, hwVapSacProfile, hwVapProfileRowStatus, 
				hwVapUserProfile, hwVapHotspot2Profile, hwSoftgreProfile, hwVapOptinon82RidUserDefined, hwVapOptinon82RidMacFormat, 
				hwVapOptinon82InsertCidFormat, hwVapOptinon82CidUserDefined, hwVapOptinon82CidMacFormat, hwVapUccProfile, 
                                                                                     hwVapAntiAttackBroadcastFloodSwitch, hwVapAntiAttackBroadcastFloodStaRateThreshold, hwVapAntiAttackBroadcastFloodBlacklistSwitch }
			STATUS current
			DESCRIPTION 
				"Description."
			::= { hwWlanConfigObjectGroups 19 }


		-- 1.3.6.1.4.1.2011.6.139.11.2.2.20
		hwSsidProfileGroups OBJECT-GROUP
			OBJECTS { hwSsidText, hwSsidHide, hwSsidAssocTimeout, hwSsidMaxStaNum, hwSsidLegacyStaSwitch, 
				hwSsidDtimInterval, hwSsidClientEdcaVoiceECWmax, hwSsidClientEdcaVoiceECWmin, hwSsidClientEdcaVoiceAIFSN, hwSsidClientEdcaVoiceTXOPLimit, 
				hwSsidClientEdcaVideoECWmax, hwSsidClientEdcaVideoECWmin, hwSsidClientEdcaVideoAIFSN, hwSsidClientEdcaVideoTXOPLimit, hwSsidClientEdcaBeECWmax, 
				hwSsidClientEdcaBeECWmin, hwSsidClientEdcaBeAIFSN, hwSsidClientEdcaBeTXOPLimit, hwSsidClientEdcaBkECWmax, hwSsidClientEdcaBkECWmin, 
				hwSsidClientEdcaBkAIFSN, hwSsidClientEdcaBkTXOPLimit, hwSsidInboundCarCir, hwSsidInboundCarPir, hwSsidInboundCarCbs, 
				hwSsidInboundCarPbs, hwSsidOutboundCarCir, hwSsidOutboundCarPir, hwSsidOutboundCarCbs, hwSsidOutboundCarPbs, 
				hwSsidProfileRowStatus, hwSsidHideWhileReachMaxSta, hwSsidBeacon2gRate, hwSsidBeacon5gRate, hwSsidDenyBroadcastProbe, 
				hwSsidProbeResponseRetry, hwSsidUapsd, hwSsidActiveDullClient }
			STATUS current
			DESCRIPTION 
				"Description."
			::= { hwWlanConfigObjectGroups 20 }


		-- 1.3.6.1.4.1.2011.6.139.11.2.2.21
		hwSecurityProfileGroups OBJECT-GROUP
			OBJECTS { hwSecurityPolicy, hwSecurityWepEncrypt, hwSecurityWepPskMode, hwSecurityWepPsk1, hwSecurityWepPsk2, 
				hwSecurityWepPsk3, hwSecurityWepPsk4, hwSecurityWepDefaultKeyId, hwSecurityWpaEncrypt, hwSecurityWpaPskMode, 
				hwSecurityWpaPsk, hwSecurityWpaPtkUpdateSwitch, hwSecurityWpaPtkUpdateInterval, hwSecurityWapiPskMode, hwSecurityWapiPsk, 
				hwSecurityWapiAsuIpAddress, hwSecurityWapiIssuerCertFileName, hwSecurityWapiAsuCertFileName, hwSecurityWapiAcCertFileName, hwSecurityWapiAcPrvKeyFileName, 
				hwSecurityWapiIssuerPfxPassword, hwSecurityWapiAsuPfxPassword, hwSecurityWapiAcPfxPassword, hwSecurityWapiAcPrvKeyPassword, hwSecurityWapiCertRetransCount, 
				hwSecurityWapiBkThreshold, hwSecurityWapiBkLifetime, hwSecurityWapiUskUpdateMethod, hwSecurityWapiMskUpdateMethod, hwSecurityWapiUskUpdateInterval, 
				hwSecurityWapiUskUpdatePackets, hwSecurityWapiUskRetansCount, hwSecurityWapiMskUpdateInterval, hwSecurityWapiMskUpdatePackets, hwSecurityWapiMskRetansCount, 
				hwSecurityWapiSATimeout, hwSecurityProfileRowStatus }
			STATUS current
			DESCRIPTION 
				"Description."
			::= { hwWlanConfigObjectGroups 21 }


		-- 1.3.6.1.4.1.2011.6.139.11.2.2.22
		hwAPTrafficProfileGroups OBJECT-GROUP
			OBJECTS { hwAPTrafficProfilePriorityMapDnTrustMode, hwAPTrafficProfilePriorityDscpDnMap80211e, hwAPTrafficProfilePriority80211eUpMapDscp, hwAPTrafficProfileUserIsolate, hwAPTrafficProfileRateLimitClientUp, 
				hwAPTrafficProfileRateLimitClientDn, hwAPTrafficProfileRateLimitVapUp, hwAPTrafficProfileRateLimitVapDn, hwAPTrafficProfileMldSnooping, hwAPTrafficProfileIGMPSnooping, 
				hwAPTrafficProfileIGMPSnoopingReportSuppress, hwAPTrafficProfileMcToUc, hwAPTrafficProfileOptimizeSuppressionBc, hwAPTrafficProfileOptimizeSuppressionUc, hwAPTrafficProfileOptimizeSuppressionMc, 
				hwAPTrafficProfileOptimizeTCPAdjustMSS, hwAPTrafficProfileOptimizeProxyARP, hwAPTrafficProfileOptimizeProxyND, hwAPTrafficProfileOptimizeUcSendARP, hwAPTrafficProfileOptimizeUcSendND, 
				hwAPTrafficProfileOptimizeUcSendDHCP, hwAPTrafficProfileOptimizeBcMcDenyAll, hwAPTrafficProfileOptimizeStaBridgeForward, hwAPTrafficProfileRowStatus, hwAPTrafficProfilePriorityMapUpTrustMode, 
				hwAPTrafficProfilePriorityDscpUpMapDscp, hwAPTrafficProfileFilterACLID, hwAPTrafficProfileFilterRowStatus
				 }
			STATUS current
			DESCRIPTION 
				"Description."
			::= { hwWlanConfigObjectGroups 22 }


		-- 1.3.6.1.4.1.2011.6.139.11.2.2.23
		hwWlanVlanPoolGroups OBJECT-GROUP
			OBJECTS { hwVlanPoolVlanlist, hwVlanPoolAssignMethod, hwVlanPoolRowStatus }
			STATUS current
			DESCRIPTION 
				"Description."
			::= { hwWlanConfigObjectGroups 23 }


		-- 1.3.6.1.4.1.2011.6.139.11.2.2.24
		hwStaWhitelistProfileGroups OBJECT-GROUP
			OBJECTS {hwWlanStaWhitelistProfileRowStatus }
			STATUS current
			DESCRIPTION 
				"Description."
			::= { hwWlanConfigObjectGroups 24 }


		-- 1.3.6.1.4.1.2011.6.139.11.2.2.25
		hwStaBlacklistProfileGroups OBJECT-GROUP
			OBJECTS { hwWlanStaBlacklistProfileRowStatus }
			STATUS current
			DESCRIPTION 
				"Description."
			::= { hwWlanConfigObjectGroups 25 }


		-- 1.3.6.1.4.1.2011.6.139.11.2.2.26
		hwWidsProfileGroups OBJECT-GROUP
			OBJECTS { hwWidsProfileRowStatus, hwWidsDeviceReportInterval, hwWidsDeviceSyncInterval, hwWidsSpoofProfile, hwWidsWhitelistProfile, 
				hwWidsBruteForceDetectInterval, hwWidsBruteForceDetectThreshold, hwWidsBruteForceQuietTime, hwWidsFloodDetectInterval, hwWidsFloodDetectThreshold, 
				hwWidsFloodQuietTime, hwWidsWeakIvQuietTime, hwWidsSpoofQuietTime, hwWidsDynamicBlackListSwitch, hwWidsRogueContainModeBmp
				 }
			STATUS current
			DESCRIPTION 
				"Description."
			::= { hwWlanConfigObjectGroups 26 }

		
		-- 1.3.6.1.4.1.2011.6.139.11.2.2.30
		hwWidsSpoofProfileGroups OBJECT-GROUP
			OBJECTS { hwWidsSpoofProfileRowStatus }
			STATUS current
			DESCRIPTION 
				"Description."
			::= { hwWlanConfigObjectGroups 30 }

			
		-- 1.3.6.1.4.1.2011.6.139.11.2.2.31
		hwWidsWhitelistProfileGroups OBJECT-GROUP
			OBJECTS { hwWidsWhitelistProfileMacRowStatus, hwWidsWhitelistProfileOuiRowStatus, hwWidsWhitelistProfileSsidRowStatus }
			STATUS current
			DESCRIPTION 
				"Description."
			::= { hwWlanConfigObjectGroups 31 }


		-- 1.3.6.1.4.1.2011.6.139.11.2.2.32
		hwMeshProfileGroups OBJECT-GROUP
			OBJECTS { hwWlanMeshID, hwWlanMeshDhcpTrustPort, hwWlanMeshLinkReportInterval, hwWlanMeshMaxLinkNum, hwWlanMeshRssiThreshold, 
				hwWlanMeshSecurityProfileName, hwWlanMeshProfileHandoverProfileName, hwWlanMeshFwaSwitch, hwWlanMeshFwaEdcaMode, hwWlanMeshProfileRowStatus, 
				hwWlanMeshClientEdcaVoiceECWmax, hwWlanMeshClientEdcaVoiceECWmin, hwWlanMeshClientEdcaVoiceAIFSN, hwWlanMeshClientEdcaVoiceTXOPLimit, hwWlanMeshClientEdcaVideoECWmax, 
				hwWlanMeshClientEdcaVideoECWmin, hwWlanMeshClientEdcaVideoAIFSN, hwWlanMeshClientEdcaVideoTXOPLimit, hwWlanMeshClientEdcaBeECWmax, hwWlanMeshClientEdcaBeECWmin, 
				hwWlanMeshClientEdcaBeAIFSN, hwWlanMeshClientEdcaBeTXOPLimit, hwWlanMeshClientEdcaBkECWmax, hwWlanMeshClientEdcaBkECWmin, hwWlanMeshClientEdcaBkAIFSN, 
				hwWlanMeshClientEdcaBkTXOPLimit, hwWlanMeshNdTrustPort, hwWlanMeshLinkAgingTime, hwWlanMeshProfilePriorityMapTrustMode, hwWlanMeshProfilePriorityDscpMap80211e
				 }
			STATUS current
			DESCRIPTION 
				"Description."
			::= { hwWlanConfigObjectGroups 32 }


		-- 1.3.6.1.4.1.2011.6.139.11.2.2.33
		hwMeshWhitelistProfileGroups OBJECT-GROUP
			OBJECTS {hwWlanMeshWhitelistProfileRowStatus, hwWlanMeshWhitelistRowStatus }
			STATUS current
			DESCRIPTION 
				"Description."
			::= { hwWlanConfigObjectGroups 33 }


		-- 1.3.6.1.4.1.2011.6.139.11.2.2.34
		hwMeshHandoverProfileGroups OBJECT-GROUP
			OBJECTS { hwWlanMeshHOLinkProbeInterval, hwWlanMeshHOMinRssiThreshold, hwWlanMeshHOMaxRssiThreshold, hwWlanMeshHOLinkHoldPeriod, hwWlanMeshHORssiMargin, 
				hwWlanMeshHOLocationBasedAlgorithmEnable, hwWlanMeshHOMovingDirection, hwWlanMeshHOPNCriteriaObserveTime, hwWlanMeshHOPNCriteriaQualifyTime, hwWlanMeshUrgentHandoverLowRateThreshold, 
				hwWlanMeshUrgentHandoverLowRatePeriod, hwWlanMeshUrgentHandoverPunishmentPeriod, hwWlanMeshUrgentHandoverPunishmentRssi, hwWlanMeshHandoverProfileRowStatus }
			STATUS current
			DESCRIPTION 
				"Description."
			::= { hwWlanConfigObjectGroups 34 }


		-- 1.3.6.1.4.1.2011.6.139.11.2.2.35
		hwWdsProfileGroups OBJECT-GROUP
			OBJECTS { hwWdsName, hwWdsMode, hwWdsDhcpTrustPort, hwWdsVlanTagged, hwWdsSecurityProfileName, 
				hwWdsProfileRowStatus, hwWdsNdTrustPort, hwWdsProfilePriorityMapTrustMode, hwWdsProfilePriorityDscpMap80211e }
			STATUS current
			DESCRIPTION 
				"Description."
			::= { hwWlanConfigObjectGroups 35 }


		-- 1.3.6.1.4.1.2011.6.139.11.2.2.36
		hwWdsWhitelistProfileGroups OBJECT-GROUP
			OBJECTS { hwWdsWhitelistProfileRowStatus,hwWdsWhitelistRowStatus }
			STATUS current
			DESCRIPTION 
				"Description."
			::= { hwWlanConfigObjectGroups 36 }

		
		-- 1.3.6.1.4.1.2011.6.139.11.2.2.37
		hwLocationProfileGroups OBJECT-GROUP
			OBJECTS {  hwLocationAeroscoutTagSwitch, hwLocationAeroscoutMuSwitch, hwLocationAeroscoutServerPort, hwLocationAeroscoutViaACSwitch, 
				hwLocationAeroscoutViaACPort, hwLocationAeroscoutCompoundTime, hwLocationEkahauTagEnable, hwLocationEkahauServerIPAddress, hwLocationEkahauServerIPv6Address, 
				hwLocationEkahauServerPort, hwLocationEkahauViaACEnable, hwLocationEkahauViaACPort, hwLocationSourceIPAddress, hwLocationSourceIPv6Address, 
				hwLocationPrivateMuEnable, hwLocationPrivateServerIPAddress, hwLocationPrivateServerIPv6Address, hwLocationPrivateServerPort, hwLocationPrivateViaACEnable, 
				hwLocationPrivateViaACPort, hwLocationPrivateReportFrequency, hwLocationProfileRowStatus }
			STATUS current
			DESCRIPTION 
				"Description."
			::= { hwWlanConfigObjectGroups 37 }
			
			
		-- 1.3.6.1.4.1.2011.6.139.11.2.2.39
		hwHotspot2ProfileGroups OBJECT-GROUP
			OBJECTS { hwHotspot2NetworkType, hwHotspot2InternetAccess, hwHotspot2VenueGroupCode, hwHotspot2VenueTypeCode, hwHotspot2Hessid, 
				hwHotspot2IPv4AddressAvail, hwHotspot2IPv6AddressAvail, hwHotspot2NetworkAuthenType, hwHotspot2RedirectUrl, hwHotspot2CarryP2PCrossConnectInfo, 
				hwHotspot2CellularNetworkProfile, hwHotspot2ConnectionCapabilityProfile, hwHotspot2OperatorNameProfile, hwHotspot2OperatingClassProfile, hwHotspot2OperatorDomainProfile, 
				hwHotspot2NaiRealmProfile, hwHotspot2VenueNameProfile, hwHotspot2RoamingConsortiumProfile, hwHotspot2ProfileRowStatus }
			STATUS current
			DESCRIPTION 
				"Description."
			::= { hwWlanConfigObjectGroups 39 }


		-- 1.3.6.1.4.1.2011.6.139.11.2.2.40
		hwCellularNetworkProfileGroups OBJECT-GROUP
			OBJECTS { hwCellularNetworkProfilePlmnIDList, hwCellularNetworkProfileRowStatus }
			STATUS current
			DESCRIPTION 
				"Description."
			::= { hwWlanConfigObjectGroups 40 }


		-- 1.3.6.1.4.1.2011.6.139.11.2.2.41
		hwConnectionCapabilityProfileGroups OBJECT-GROUP
			OBJECTS { hwConnectionCapabilityEsp, hwConnectionCapabilityIcmp, hwConnectionCapabilityTcpFtp, hwConnectionCapabilityTcpHttp, hwConnectionCapabilityTcpPptpVpn, 
				hwConnectionCapabilityTcpSsh, hwConnectionCapabilityTcpTlsVpn, hwConnectionCapabilityTcpVoip, hwConnectionCapabilityUdpIke2Port4500, hwConnectionCapabilityUdpIke2Port500, 
				hwConnectionCapabilityUdpVoip, hwConnectionCapabilityProfileRowStatus }
			STATUS current
			DESCRIPTION 
				"Description."
			::= { hwWlanConfigObjectGroups 41 }


		-- 1.3.6.1.4.1.2011.6.139.11.2.2.42
		hwOperatorNameProfileGroups OBJECT-GROUP
			OBJECTS { hwOperatorNameLanguageCodeList, hwOperatorFriendlyNameList, hwOperatorNameProfileRowStatus }
			STATUS current
			DESCRIPTION 
				"Description."
			::= { hwWlanConfigObjectGroups 42 }


		-- 1.3.6.1.4.1.2011.6.139.11.2.2.43
		hwOperatorClassProfileGroups OBJECT-GROUP
			OBJECTS { hwOperatorClassIndicationList, hwOperatorClassProfileRowStatus }
			STATUS current
			DESCRIPTION 
				"Description."
			::= { hwWlanConfigObjectGroups 43 }


		-- 1.3.6.1.4.1.2011.6.139.11.2.2.44
		hwOperatorDomainNameProfileGroups OBJECT-GROUP
			OBJECTS { hwOperatorDomainNameList, hwOperatorDomainNameProfileRowStatus }
			STATUS current
			DESCRIPTION 
				"Description."
			::= { hwWlanConfigObjectGroups 44 }

			
		-- 1.3.6.1.4.1.2011.6.139.11.2.2.45
		hwNAIRealmProfileGroups OBJECT-GROUP
			OBJECTS {hwNAIRealmEapAuthenPara, 
				hwNAIRealmProfileRowStatus,hwNAIRealmProfileListRowStatus }
			STATUS current
			DESCRIPTION 
				"Description."
			::= { hwWlanConfigObjectGroups 45 }


		-- 1.3.6.1.4.1.2011.6.139.11.2.2.46
		hwVenueNameProfileGroups OBJECT-GROUP
			OBJECTS { hwVenueNameLanguageCodeList, hwVenueNameList, hwVenueNameProfileRowStatus }
			STATUS current
			DESCRIPTION 
				"Description."
			::= { hwWlanConfigObjectGroups 46 }


		-- 1.3.6.1.4.1.2011.6.139.11.2.2.47
		hwRoamingConsortiumProfileGroups OBJECT-GROUP
			OBJECTS {hwRoamingConsortiumOIList, hwRoamingConsortiumOIInBeaconList, hwRoamingConsortiumProfileRowStatus }
			STATUS current
			DESCRIPTION 
				"Description."
			::= { hwWlanConfigObjectGroups 47 }


		-- 1.3.6.1.4.1.2011.6.139.11.2.2.48
		hwSACProfileGroups OBJECT-GROUP
			OBJECTS {hwSACProfUserStat, hwSACProfVapStat, hwSACProfRowStatus }
			STATUS current
			DESCRIPTION 
				"Description."
			::= { hwWlanConfigObjectGroups 48 }


		-- 1.3.6.1.4.1.2011.6.139.11.2.2.49
		hwSACProfActionGroups OBJECT-GROUP
			OBJECTS { hwSACProfileActProtocolType, hwSACProfileActProtocolName, hwSACProfileActProtocolGrpName, hwSACProfileActionType, hwSACProfileActCarCir, 
				hwSACProfileActRemarkDscpValue, hwSACProfileActRemark8021pValue, hwSACProfileActionRowstatus }
			STATUS current
			DESCRIPTION 
				"Description."
			::= { hwWlanConfigObjectGroups 49 }

		
		-- 1.3.6.1.4.1.2011.6.139.11.2.2.50
		hwAPProvisionGroups OBJECT-GROUP
			OBJECTS { hwWlanAPProvisionAddressMode, hwWlanAPProvisionIPv4Address, hwWlanAPProvisionIPv4Mask, hwWlanAPProvisionIPv4Gateway, hwWlanAPProvisionIPv6Address, 
				hwWlanAPProvisionIPv6PrefixLen, hwWlanAPProvisionIPv6Gateway, hwWlanAPProvisionGroupName, hwWlanAPProvisionName, hwWlanAPProvisionIPv4ACList, 
				hwWlanAPProvisionIPv6ACList, hwWlanAPProvisionCommitAPName, hwWlanAPProvisionCommitAPMac, hwWlanAPProvisionCommitAPGroup }
			STATUS current
			DESCRIPTION 
				"Description."
			::= { hwWlanConfigObjectGroups 50 }


		-- 1.3.6.1.4.1.2011.6.139.11.2.2.51
		hwWlanRadioCalibrateManagementGroups OBJECT-GROUP
			OBJECTS { hwWlanRadioCalibrateMode, hwWlanRadioCalibrateScheduleTime, hwWlanRadioCalibrateManualStartup, hwWlanRadioCalibrateAutoInterval, hwWlanRadioCalibratePolicy, 
				hwWlanRadioCalibrateSensitivity, hwWlanRadioCalibrateAutoStartTime }
			STATUS current
			DESCRIPTION 
				"Description."
			::= { hwWlanConfigObjectGroups 51 }


		-- 1.3.6.1.4.1.2011.6.139.11.2.2.52
		hwWlanMobilityGroups OBJECT-GROUP
			OBJECTS { hwWlanMasterControllerSwitch, hwWlanConnectMasterControllerSwitch, hwWlanConnectMasterControllerIPv4Addr, hwWlanConnectMasterControllerIPv6Addr, hwWlanAcIPv4Address, 
				hwWlanAcIPv6Address, hwWlanAcState, hwWlanAcRowStatus, hwWlanMobilityGroupRowStatus, hwWlanMobilityGroupMemberRowStatus
				 }
			STATUS current
			DESCRIPTION 
				"Description."
			::= { hwWlanConfigObjectGroups 52 }


		-- 1.3.6.1.4.1.2011.6.139.11.2.2.53
		hwWlanLanguageGroups OBJECT-GROUP
			OBJECTS { hwWlanLanguageCodeDescription }
			STATUS current
			DESCRIPTION 
				"Description."
			::= { hwWlanConfigObjectGroups 53 }


		-- 1.3.6.1.4.1.2011.6.139.11.2.2.54
		hwFatApConfigGroups OBJECT-GROUP
			OBJECTS { hwFatApCountryCode, hwFatApMaxStaNum, hwFatApStaAccessMode, hwFatApStaAccessModePorfile, hwFatApHighTempThreshold, 
				hwFatApLowTempThreshold, hwFatApDcaChannel5GBandwidth, hwFatApDcaChannel5GChannelSet, hwFatApDcaChannel2GChannelSet, hwFatApDynamicBlackAgingTime, 
				hwFatApAntennaOutputMode, hwFatApRadio0Frequency, hwFatApRadio2gProfile, hwFatApRadio5gProfile, hwFatApRadioMeshProfile, 
				hwFatApLocationProfile, hwFatApRadioRowStatus, hwFatApMeshWhitelistProfile, hwFatApWdsWhitelistProfile, hwFatApRadioSwitch, 
				hwFatApRadioChannel, hwFatApRadioBandwidth, hwFatApRadioEirp, hwFatApRadioAntennaGain, hwFatApRadioCoverageDistance, 
				hwFatApRadioWorkMode, hwFatApWidsDeviceDetectSwitch, hwFatApWidsAttackDetectEnBmp, hwFatApWidsRogueContainSwitch, 
				hwFatApVapProfile, hwFatApVapProfileRowStatus
				 }
			STATUS current
			DESCRIPTION 
				"Description."
			::= { hwWlanConfigObjectGroups 54 }

		

		-- 1.3.6.1.4.1.2011.6.139.11.2.2.55
		hwWidsSpoofProfileListGroups OBJECT-GROUP
			OBJECTS { hwWidsSpoofProfileListRowStatus }
			STATUS current
			DESCRIPTION 
				"Description."
			::= { hwWlanConfigObjectGroups 55 }

		
		-- 1.3.6.1.4.1.2011.6.139.11.2.2.56
		hwWidsWhitelistProfileListGroups OBJECT-GROUP
			OBJECTS {hwWidsWhitelistProfileListRowStatus }
			STATUS current
			DESCRIPTION 
				"Description."
			::= { hwWlanConfigObjectGroups 56 }

		
		-- 1.3.6.1.4.1.2011.6.139.11.2.2.57
		hwWlanLoadBalanceStaticGroupGroups OBJECT-GROUP
			OBJECTS { hwWlanLBGapThreshold, hwWlanLBDenyThreshold, hwWlanLBStartThreshold, hwWlanLBGroupStatus, 
				hwWlanLBGroupRowStatus }
			STATUS current
			DESCRIPTION 
				"Description."
			::= { hwWlanConfigObjectGroups 57 }

		
		-- 1.3.6.1.4.1.2011.6.139.11.2.2.58
		hwWlanLoadBalanceStaticGroupMemberGroups OBJECT-GROUP
			OBJECTS { hwWlanLBMemberRowStatus }
			STATUS current
			DESCRIPTION 
				"Description."
			::= { hwWlanConfigObjectGroups 58 }


		-- 1.3.6.1.4.1.2011.6.139.11.2.2.59
		hwWlanCountryCodeGroups OBJECT-GROUP
			OBJECTS { hwWlanCountryCodeEngDescription, hwWlanCountryCodeAvailableChannelSet2gBW20, hwWlanCountryCodeAvailableChannelSet2gBW40Plus, hwWlanCountryCodeAvailableChannelSet2gBW40Minus, hwWlanCountryCodeAvailableChannelSet5gBW20,
				hwWlanCountryCodeAvailableChannelSet5gBW40Plus, hwWlanCountryCodeAvailableChannelSet5gBW40Minus, hwWlanCountryCodeAvailableChannelSet5gBW80,
				hwWlanCountryCodeAvailableChannelSet5gBW160 }
			STATUS current
			DESCRIPTION 
				"Description."
			::= { hwWlanConfigObjectGroups 59 }
		
		-- 1.3.6.1.4.1.2011.6.139.11.2.2.60
		hwUccProfileGroups OBJECT-GROUP
			OBJECTS { hwUCCProfLyncVoice8021p, hwUCCProfLyncVoice8021pValue, hwUCCProfLyncVoiceDscp, hwUCCProfLyncVoiceDscpValue, hwUCCProfLyncVideo8021p, 
				hwUCCProfLyncVideo8021pValue, hwUCCProfLyncVideoDscp, hwUCCProfLyncVideoDscpValue, hwUCCProfLyncShare8021p, hwUCCProfLyncShare8021pValue, 
				hwUCCProfLyncShareDscp, hwUCCProfLyncShareDscpValue, hwUCCProfLyncFileTransfer8021p, hwUCCProfLyncFileTransfer8021pValue, hwUCCProfLyncFileTransferDscp, 
				hwUCCProfLyncFileTransferDscpValue, hwUCCProfileRowStatus }
			STATUS current
			DESCRIPTION 
				"Description."
			::= { hwWlanConfigObjectGroups 60 }
		
		-- 1.3.6.1.4.1.2011.6.139.11.2.2.61
		hwSoftgreProfileGroups OBJECT-GROUP
			OBJECTS { hwSoftgreDestinationIPAddress, hwSoftgreDestinationIPv6Address, hwSoftgreKeepaliveFlag, hwSoftgreKeepalivePeriod, 
				hwSoftgreKeepaliveRetryTimes, hwSoftgreProfileRowStatus }
			STATUS current
			DESCRIPTION 
				"Description."
			::= { hwWlanConfigObjectGroups 61 }
	
		-- 1.3.6.1.4.1.2011.6.139.11.2.2.66
		hwBleProfileGroups OBJECT-GROUP
			OBJECTS { hwWlanBLEBroadcasterEnable, hwWlanBLETxPower, hwWlanBLEBroadcastingUUID, hwWlanBLEBroadcastingMajor, 
				hwWlanBLEBroadcastingMinor, hwWlanBLEBroadcastingReferenceRSSI, hwWlanBLEBroadcastingInterval, hwWlanBLESnifferEnable, 
				hwWlanBLEProfileRowStatus }
			STATUS current
			DESCRIPTION 
				"Description."
			::= { hwWlanConfigObjectGroups 66 }

		-- 1.3.6.1.4.1.2011.6.139.11.2.2.67
		hwAPGroupCardGroups OBJECT-GROUP
			OBJECTS { hwAPGrpCardSerialProfile, hwAPGrpCardProfile, hwAPGrpCardNetUDPPort, hwAPGrpIoTRowStatus }
			STATUS current
			DESCRIPTION 
				"Description."
			::= { hwWlanConfigObjectGroups 67 }

		-- 1.3.6.1.4.1.2011.6.139.11.2.2.68
		hwAPSpecificCardGroups OBJECT-GROUP
			OBJECTS { hwAPSpIoTSerialProfile, hwAPSpIoTProfile, hwAPSpIoTNetUDPPort, hwAPSpIoTRowStatus }
			STATUS current
			DESCRIPTION 
				"Description."
			::= { hwWlanConfigObjectGroups 68 }

		-- 1.3.6.1.4.1.2011.6.139.11.2.2.69
		hwIoTSerialProfileGroups OBJECT-GROUP
			OBJECTS { hwIoTSerialSpeed, hwIoTSerialParity, hwIoTSerialStopbits, hwIoTSerialFrameFormat, hwIoTSerialFrameLength, 
			  hwIoTSerialFrameStart, hwIoTSerialFrameStop, hwIoTSerialProfileRowStatus }
			STATUS current
			DESCRIPTION 
				"Description."
			::= { hwWlanConfigObjectGroups 69 }

		-- 1.3.6.1.4.1.2011.6.139.11.2.2.70
		hwIoTProfileGroups OBJECT-GROUP
			OBJECTS { hwIoTProfileConfigAgentPermitIp, hwIoTProfileConfigAgentPermitMaskLen, hwIoTProfileShareKey, hwIoTProfileRowStatus }
			STATUS current
			DESCRIPTION 
				"Description."
			::= { hwWlanConfigObjectGroups 70 }
			
		-- 1.3.6.1.4.1.2011.6.139.11.2.2.71
		hwIoTProfileManagementServerGroups OBJECT-GROUP
			OBJECTS { hwIoTProfileManagementServerIp, hwIoTProfileManagementServerPort, hwIoTProfileManagementServerRowStatus }
			STATUS current
			DESCRIPTION 
				"Description."
			::= { hwWlanConfigObjectGroups 71 }
												
	END
--
-- HUAWEI-WLAN-CONFIGURATION-MIB.mib
--
